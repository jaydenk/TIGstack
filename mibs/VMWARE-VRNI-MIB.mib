-- **********************************************************
-- Copyright 2016 - 2018 VMware, Inc.  All rights reserved.
-- **********************************************************

VMWARE-VRNI-MIB DEFINITIONS ::= BEGIN

IMPORTS
   MODULE-IDENTITY, OBJECT-IDENTITY, OBJECT-TYPE, NOTIFICATION-TYPE
       FROM SNMPv2-SMI
   SnmpAdminString
       FROM SNMP-FRAMEWORK-MIB
   MODULE-COMPLIANCE, OBJECT-GROUP, NOTIFICATION-GROUP
       FROM SNMPv2-CONF
   TEXTUAL-CONVENTION, DateAndTime
       FROM SNMPv2-TC
   vmwNetworkInsight
       FROM VMWARE-ROOT-MIB
   VmwLongSnmpAdminString
       FROM VMWARE-TC-MIB;

    vmwNetworkInsightMIB MODULE-IDENTITY
    LAST-UPDATED "201811270000Z"
    ORGANIZATION "VMware, Inc"
    CONTACT-INFO
    "VMware, Inc
    3401 Hillview Ave
    Palo Alto, CA 94304
    Tel: 1-877-486-9273 or 650-427-5000
    Fax: 650-427-5001
    Web: http://communities.vmware.com/community/developer/forums/managementapi
    "

    DESCRIPTION
    "This MIB module is for VMware vRealize Network Insight as described here:
    https://www.vmware.com/support/pubs/vrealize-network-insight-pubs.html
    "

    REVISION      "201811270000Z"
    DESCRIPTION
    "This is the sixth revision of VMware vRealize Network Insight Manager SNMP notifications.
    It adds fourteen new notifications, see vmwNetworkInsightNotificationGroup6.
    "

    REVISION      "201809120000Z"
    DESCRIPTION
    "This is the fifth revision of VMware vRealize Network Insight Manager SNMP notifications.
    This revision introduces below changes, some of which are non backward compatible.
      a. All event notifications have their varbind contents changed
        from : OBJECTS { vmwAffectedObject, vmwEventSeverity, vmwVrniUrl, vmwTimestamp, vmwOperatorDesc, vmwEventName}
        to : OBJECTS { vmwEventSeverity, vmwAffectedObject, vmwOperatorDesc, vmwVrniUrl, vmwTimestamp, vmwEventName }

      b. Syntax changes for TC - VmwVrniSeverity
        was { cleared(0), info(1), major(2) }
        is now VmwVrniSeverity {Critical, Moderate, Warning, Info and CLEARED}

      c. Support for new events added, see vmwNetworkInsightNotificationGroup5
      "

    REVISION      "201709050000Z"
    DESCRIPTION
    "This is the fourth revision of VMware vRealize Network Insight Manager SNMP notifications.
    It adds fourteen new notifications, see vmwNetworkInsightNotificationGroup4.
    "

   REVISION     "201706010000Z"
   DESCRIPTION
    "This is the third revision of VMware vRealize Network Insight Manager SNMP notifications.
     This version added nineteen new notifications, see vmwNetworkInsightNotificationGroup3
     for complete listing."

    REVISION      "201702200000Z"
    DESCRIPTION
    "This is the second revision of VMware vRealize Network Insight Manager SNMP notifications.
     It introduces new notifications, see vmwNetworkInsightNotificationGroup2,
     and updates existing notifications to append the vmwEventName managed object."


    REVISION      "201610260000Z"
    DESCRIPTION
    "This is the first revision of VMware vRealize Network Insight Manager SNMP notifications."
    ::= { vmwNetworkInsight 1 }


vmwVRNIEvents OBJECT-IDENTITY
    STATUS  current
    DESCRIPTION
    "All notifications from vRealize Network Insight fall under this oid."
    ::= { vmwNetworkInsightMIB 0 }

vmwVRNIData OBJECT-IDENTITY
    STATUS  current
    DESCRIPTION
    "All variables that are sent in notifications fall under this oid."
    ::= { vmwNetworkInsightMIB 1 }

-- **********************************************************
-- Type definitions
-- **********************************************************

  VmwVrniSeverity ::= TEXTUAL-CONVENTION
    DISPLAY-HINT "255t"
    STATUS          current
    DESCRIPTION
        "Represents Event Severity, the values returned by TC are
        Critical - All events which are critical in nature towards overall health of environment, could be show stoppers if not fixed
        Moderate - Represents moderate severity, part of functionality could get affected
        Warning - Event which may not represent immediate issue but could soon become one if not addressed
        Info - Informational notifications
        CLEARED - Event was closed by system.
        "
    SYNTAX       OCTET STRING (SIZE (0..255))

-- **********************************************************
-- Notifications by an agent that implements this mib module
-- **********************************************************

vmwSnmpTrapsAreConfigured NOTIFICATION-TYPE
   OBJECTS { vmwEventSeverity, vmwAffectedObject, vmwOperatorDesc, vmwVrniUrl, vmwTimestamp, vmwEventName }
   STATUS current
   DESCRIPTION
      "Initial trap to notify receiver that vRNI is now configured to send SNMP traps"
   ::= { vmwVRNIEvents 101}


vmwSnmpTrapsAreDisabled NOTIFICATION-TYPE
   OBJECTS { vmwEventSeverity, vmwAffectedObject, vmwOperatorDesc, vmwVrniUrl, vmwTimestamp, vmwEventName }
   STATUS current
   DESCRIPTION
      "Trap to notify receiver that vRNI is no longer configured to send SNMP traps"
   ::= { vmwVRNIEvents 102}


vmwTestTrap NOTIFICATION-TYPE
   OBJECTS { vmwEventSeverity, vmwAffectedObject, vmwOperatorDesc, vmwVrniUrl, vmwTimestamp, vmwEventName }
   STATUS current
   DESCRIPTION
      "Test Trap"
   ::= { vmwVRNIEvents 103}


vmwEntityDiscoveryChangeEvent NOTIFICATION-TYPE
   OBJECTS { vmwEventSeverity, vmwAffectedObject, vmwOperatorDesc, vmwVrniUrl, vmwTimestamp, vmwEventName }
   STATUS current
   DESCRIPTION
      "Discovery Event"
   ::= { vmwVRNIEvents 20001}

vmwEntityPropertiesChangeEvent NOTIFICATION-TYPE
   OBJECTS { vmwEventSeverity, vmwAffectedObject, vmwOperatorDesc, vmwVrniUrl, vmwTimestamp, vmwEventName }
   STATUS current
   DESCRIPTION
      "Property Change Event"
   ::= { vmwVRNIEvents 20002}

vmwFirewallNotInstalledOnHostEvent NOTIFICATION-TYPE
   OBJECTS { vmwEventSeverity, vmwAffectedObject, vmwOperatorDesc, vmwVrniUrl, vmwTimestamp, vmwEventName }
   STATUS current
   DESCRIPTION
      "Firewall Not Installed On Host Event"
   ::= { vmwVRNIEvents 20003}

vmwHostWithStaleFirewallRulesEvent NOTIFICATION-TYPE
   OBJECTS { vmwEventSeverity, vmwAffectedObject, vmwOperatorDesc, vmwVrniUrl, vmwTimestamp, vmwEventName }
   STATUS current
   DESCRIPTION
      "Host With Stale Firewall Rules Event"
   ::= { vmwVRNIEvents 20004}

vmwIpAddressChangeEvent NOTIFICATION-TYPE
   OBJECTS { vmwEventSeverity, vmwAffectedObject, vmwOperatorDesc, vmwVrniUrl, vmwTimestamp, vmwEventName }
   STATUS current
   DESCRIPTION
      "Ip Address Change"
   ::= { vmwVRNIEvents 20005}

vmwL2GatewayAnomalyEvent NOTIFICATION-TYPE
   OBJECTS { vmwEventSeverity, vmwAffectedObject, vmwOperatorDesc, vmwVrniUrl, vmwTimestamp, vmwEventName }
   STATUS current
   DESCRIPTION
      "L2 Gateway Anomaly Event"
   ::= { vmwVRNIEvents 20006}

vmwL2NetworkAddressAnomalyEvent NOTIFICATION-TYPE
   OBJECTS { vmwEventSeverity, vmwAffectedObject, vmwOperatorDesc, vmwVrniUrl, vmwTimestamp, vmwEventName }
   STATUS current
   DESCRIPTION
      "L2 Network Address Anomaly Event"
   ::= { vmwVRNIEvents 20007}

vmwL2NetworkDiameterExceededEvent NOTIFICATION-TYPE
   OBJECTS { vmwEventSeverity, vmwAffectedObject, vmwOperatorDesc, vmwVrniUrl, vmwTimestamp, vmwEventName }
   STATUS current
   DESCRIPTION
      "L2 Network Diameter Exceeded Event"
   ::= { vmwVRNIEvents 20008}

vmwL2NetworkUplinkMissingEvent NOTIFICATION-TYPE
   OBJECTS { vmwEventSeverity, vmwAffectedObject, vmwOperatorDesc, vmwVrniUrl, vmwTimestamp, vmwEventName }
   STATUS current
   DESCRIPTION
      "L2 Network Uplink Missing Event"
   ::= { vmwVRNIEvents 20009}

vmwL2NetworkWithNoVMsEvent NOTIFICATION-TYPE
   OBJECTS { vmwEventSeverity, vmwAffectedObject, vmwOperatorDesc, vmwVrniUrl, vmwTimestamp, vmwEventName }
   STATUS current
   DESCRIPTION
      "L2 Network With No VMs Event"
   ::= { vmwVRNIEvents 20010}

vmwLayer2NetworkDiameterChangedEvent NOTIFICATION-TYPE
   OBJECTS { vmwEventSeverity, vmwAffectedObject, vmwOperatorDesc, vmwVrniUrl, vmwTimestamp, vmwEventName }
   STATUS current
   DESCRIPTION
      "Layer2 Network Diameter Changed Event"
   ::= { vmwVRNIEvents 20011}

vmwMTUMismatchEvent NOTIFICATION-TYPE
   OBJECTS { vmwEventSeverity, vmwAffectedObject, vmwOperatorDesc, vmwVrniUrl, vmwTimestamp, vmwEventName }
   STATUS current
   DESCRIPTION
      "MTU Mismatch Event"
   ::= { vmwVRNIEvents 20012}

vmwNetworkIsolationEvent NOTIFICATION-TYPE
   OBJECTS { vmwEventSeverity, vmwAffectedObject, vmwOperatorDesc, vmwVrniUrl, vmwTimestamp, vmwEventName }
   STATUS current
   DESCRIPTION
      "Network Isolation Event"
   ::= { vmwVRNIEvents 20013}

vmwNoPathEvent NOTIFICATION-TYPE
   OBJECTS { vmwEventSeverity, vmwAffectedObject, vmwOperatorDesc, vmwVrniUrl, vmwTimestamp, vmwEventName }
   STATUS current
   DESCRIPTION
      "No Path Event"
   ::= { vmwVRNIEvents 20014}

vmwSpoofguardDisabledEvent NOTIFICATION-TYPE
   OBJECTS { vmwEventSeverity, vmwAffectedObject, vmwOperatorDesc, vmwVrniUrl, vmwTimestamp, vmwEventName }
   STATUS current
   DESCRIPTION
      "Spoofguard Disabled Event"
   ::= { vmwVRNIEvents 20015}

vmwVMotionEvent NOTIFICATION-TYPE
   OBJECTS { vmwEventSeverity, vmwAffectedObject, vmwOperatorDesc, vmwVrniUrl, vmwTimestamp, vmwEventName }
   STATUS current
   DESCRIPTION
      "VMotion Event"
   ::= { vmwVRNIEvents 20018}

vmwVMWithDisconnectedVnicsEvent NOTIFICATION-TYPE
   OBJECTS { vmwEventSeverity, vmwAffectedObject, vmwOperatorDesc, vmwVrniUrl, vmwTimestamp, vmwEventName }
   STATUS current
   DESCRIPTION
      "VM With Disconnected Vnics Event"
   ::= { vmwVRNIEvents 20019}

vmwVMWithMulipleVnicsOnDifferentVxlansEvent NOTIFICATION-TYPE
   OBJECTS { vmwEventSeverity, vmwAffectedObject, vmwOperatorDesc, vmwVrniUrl, vmwTimestamp, vmwEventName }
   STATUS current
   DESCRIPTION
      "VM With Multiple Vnics On Different Vxlans Event"
   ::= { vmwVRNIEvents 20020}

vmwVMWithMulipleVnicsOnSameL2Event NOTIFICATION-TYPE
   OBJECTS { vmwEventSeverity, vmwAffectedObject, vmwOperatorDesc, vmwVrniUrl, vmwTimestamp, vmwEventName }
   STATUS current
   DESCRIPTION
      "VM With Multiple Vnics On Same L2 Event"
   ::= { vmwVRNIEvents 20021}

vmwVMWithNoIpAddressEvent NOTIFICATION-TYPE
   OBJECTS { vmwEventSeverity, vmwAffectedObject, vmwOperatorDesc, vmwVrniUrl, vmwTimestamp, vmwEventName }
   STATUS current
   DESCRIPTION
      "VM With No Ip Address Event"
   ::= { vmwVRNIEvents 20022}

vmwVTEPMissingEvent NOTIFICATION-TYPE
   OBJECTS { vmwEventSeverity, vmwAffectedObject, vmwOperatorDesc, vmwVrniUrl, vmwTimestamp, vmwEventName }
   STATUS current
   DESCRIPTION
      "VTEP Missing Event"
   ::= { vmwVRNIEvents 20023}

vmwL2Event NOTIFICATION-TYPE
   OBJECTS { vmwEventSeverity, vmwAffectedObject, vmwOperatorDesc, vmwVrniUrl, vmwTimestamp, vmwEventName }
   STATUS current
   DESCRIPTION
      "L2 Event"
   ::= { vmwVRNIEvents 20024}

vmwMembershipChangeEvent NOTIFICATION-TYPE
   OBJECTS { vmwEventSeverity, vmwAffectedObject, vmwOperatorDesc, vmwVrniUrl, vmwTimestamp, vmwEventName }
   STATUS current
   DESCRIPTION
      "Membership Change"
   ::= { vmwVRNIEvents 20025}

vmwSecurityGroupMembershipChangeEvent NOTIFICATION-TYPE
   OBJECTS { vmwEventSeverity, vmwAffectedObject, vmwOperatorDesc, vmwVrniUrl, vmwTimestamp, vmwEventName }
   STATUS current
   DESCRIPTION
      "Security Group Membership Change"
   ::= { vmwVRNIEvents 20026}

vmwFirewallRuleMembershipChangeEvent NOTIFICATION-TYPE
   OBJECTS { vmwEventSeverity, vmwAffectedObject, vmwOperatorDesc, vmwVrniUrl, vmwTimestamp, vmwEventName }
   STATUS current
   DESCRIPTION
      "Firewall Rule Membership Change"
   ::= { vmwVRNIEvents 20027}

vmwVlanMembershipChangeEvent NOTIFICATION-TYPE
   OBJECTS { vmwEventSeverity, vmwAffectedObject, vmwOperatorDesc, vmwVrniUrl, vmwTimestamp, vmwEventName }
   STATUS current
   DESCRIPTION
      "Vlan Membership Change"
   ::= { vmwVRNIEvents 20028}

vmwVxlanMembershipChangeEvent NOTIFICATION-TYPE
   OBJECTS { vmwEventSeverity, vmwAffectedObject, vmwOperatorDesc, vmwVrniUrl, vmwTimestamp, vmwEventName }
   STATUS current
   DESCRIPTION
      "Vxlan Membership Change"
   ::= { vmwVRNIEvents 20029}

vmwDeleteChangeEvent NOTIFICATION-TYPE
   OBJECTS { vmwEventSeverity, vmwAffectedObject, vmwOperatorDesc, vmwVrniUrl, vmwTimestamp, vmwEventName }
   STATUS current
   DESCRIPTION
      "Delete Event"
   ::= { vmwVRNIEvents 20030}

vmwVtepFailedPingEvent NOTIFICATION-TYPE
   OBJECTS { vmwEventSeverity, vmwAffectedObject, vmwOperatorDesc, vmwVrniUrl, vmwTimestamp, vmwEventName }
   STATUS current
   DESCRIPTION
      "VTEP Ping Failure Event"
   ::= { vmwVRNIEvents 20031}

vmwEmptySearchStreamChangeEvent NOTIFICATION-TYPE
   OBJECTS { vmwEventSeverity, vmwAffectedObject, vmwOperatorDesc, vmwVrniUrl, vmwTimestamp, vmwEventName }
   STATUS current
   DESCRIPTION
      "Search with no results"
   ::= { vmwVRNIEvents 20034}

vmwSearchStreamMembershipChangeEvent NOTIFICATION-TYPE
   OBJECTS { vmwEventSeverity, vmwAffectedObject, vmwOperatorDesc, vmwVrniUrl, vmwTimestamp, vmwEventName }
   STATUS current
   DESCRIPTION
      "Search results changed"
   ::= { vmwVRNIEvents 20035}

vmwEmptySearchStreamProblemEvent NOTIFICATION-TYPE
   OBJECTS { vmwEventSeverity, vmwAffectedObject, vmwOperatorDesc, vmwVrniUrl, vmwTimestamp, vmwEventName }
   STATUS current
   DESCRIPTION
      "Search with no results (Problem)"
   ::= { vmwVRNIEvents 20036}

vmwSearchStreamMembershipProblemEvent NOTIFICATION-TYPE
   OBJECTS { vmwEventSeverity, vmwAffectedObject, vmwOperatorDesc, vmwVrniUrl, vmwTimestamp, vmwEventName }
   STATUS current
   DESCRIPTION
      "Search results changed (Problem)"
   ::= { vmwVRNIEvents 20037}

vmwOspfConfigurationMismatchEvent NOTIFICATION-TYPE
   OBJECTS { vmwEventSeverity, vmwAffectedObject, vmwOperatorDesc, vmwVrniUrl, vmwTimestamp, vmwEventName }
   STATUS current
   DESCRIPTION
      "OSPF Mismatch Event"
   ::= { vmwVRNIEvents 20038}

vmwServiceVMNotHealthyEvent NOTIFICATION-TYPE
   OBJECTS { vmwEventSeverity, vmwAffectedObject, vmwOperatorDesc, vmwVrniUrl, vmwTimestamp, vmwEventName }
   STATUS current
   DESCRIPTION
      "Service VM Not Healthy Event"
   ::= { vmwVRNIEvents 20039}

vmwServiceVMNotPoweredOnEvent NOTIFICATION-TYPE
   OBJECTS { vmwEventSeverity, vmwAffectedObject, vmwOperatorDesc, vmwVrniUrl, vmwTimestamp, vmwEventName }
   STATUS current
   DESCRIPTION
      "Service VM Not Powered On Event"
   ::= { vmwVRNIEvents 20040}

vmwServiceVMHighCPUUsageEvent NOTIFICATION-TYPE
   OBJECTS { vmwEventSeverity, vmwAffectedObject, vmwOperatorDesc, vmwVrniUrl, vmwTimestamp, vmwEventName }
   STATUS current
   DESCRIPTION
      "Service VM High CPU Usage Event"
   ::= { vmwVRNIEvents 20041}

vmwServiceVMHighMemoryUsageEvent NOTIFICATION-TYPE
   OBJECTS { vmwEventSeverity, vmwAffectedObject, vmwOperatorDesc, vmwVrniUrl, vmwTimestamp, vmwEventName }
   STATUS current
   DESCRIPTION
      "Service VM High Memory Usage Event"
   ::= { vmwVRNIEvents 20042}

vmwServiceVMHighDiskUsageEvent NOTIFICATION-TYPE
   OBJECTS { vmwEventSeverity, vmwAffectedObject, vmwOperatorDesc, vmwVrniUrl, vmwTimestamp, vmwEventName }
   STATUS current
   DESCRIPTION
      "Service VM High Disk Usage Event"
   ::= { vmwVRNIEvents 20043}

vmwIPSetPropertiesChangeEvent NOTIFICATION-TYPE
   OBJECTS { vmwEventSeverity, vmwAffectedObject, vmwOperatorDesc, vmwVrniUrl, vmwTimestamp, vmwEventName }
   STATUS current
   DESCRIPTION
      "IPSet Change"
   ::= { vmwVRNIEvents 20050}

vmwFirewallRulePropertiesChangeEvent NOTIFICATION-TYPE
   OBJECTS { vmwEventSeverity, vmwAffectedObject, vmwOperatorDesc, vmwVrniUrl, vmwTimestamp, vmwEventName }
   STATUS current
   DESCRIPTION
      "Firewall Rule Change"
   ::= { vmwVRNIEvents 20051}

vmwSecurityGroupPropertiesChangeEvent NOTIFICATION-TYPE
   OBJECTS { vmwEventSeverity, vmwAffectedObject, vmwOperatorDesc, vmwVrniUrl, vmwTimestamp, vmwEventName }
   STATUS current
   DESCRIPTION
      "Security Group Change"
   ::= { vmwVRNIEvents 20052}

vmwIPSetMembershipChangeEvent NOTIFICATION-TYPE
   OBJECTS { vmwEventSeverity, vmwAffectedObject, vmwOperatorDesc, vmwVrniUrl, vmwTimestamp, vmwEventName }
   STATUS current
   DESCRIPTION
      "IPSet Membership Change"
   ::= { vmwVRNIEvents 20053}

vmwFirewallRuleMaskEvent NOTIFICATION-TYPE
   OBJECTS { vmwEventSeverity, vmwAffectedObject, vmwOperatorDesc, vmwVrniUrl, vmwTimestamp, vmwEventName }
   STATUS current
   DESCRIPTION
      "Firewall Rule Masked Event"
   ::= { vmwVRNIEvents 20054}

vmwSecurityMembershipChangeEvent NOTIFICATION-TYPE
   OBJECTS { vmwEventSeverity, vmwAffectedObject, vmwOperatorDesc, vmwVrniUrl, vmwTimestamp, vmwEventName }
   STATUS current
   DESCRIPTION
      "Security Membership Change"
   ::= { vmwVRNIEvents 20056}

vmwSecurityTagPropertiesChangeEvent NOTIFICATION-TYPE
   OBJECTS { vmwEventSeverity, vmwAffectedObject, vmwOperatorDesc, vmwVrniUrl, vmwTimestamp, vmwEventName }
   STATUS current
   DESCRIPTION
      "Security Tag Change"
   ::= { vmwVRNIEvents 20057}

vmwSecurityTagMembershipChangeEvent NOTIFICATION-TYPE
   OBJECTS { vmwEventSeverity, vmwAffectedObject, vmwOperatorDesc, vmwVrniUrl, vmwTimestamp, vmwEventName }
   STATUS current
   DESCRIPTION
      "Security Tag Membership Change"
   ::= { vmwVRNIEvents 20058}

vmwHostDatastoreChangeEvent NOTIFICATION-TYPE
   OBJECTS { vmwEventSeverity, vmwAffectedObject, vmwOperatorDesc, vmwVrniUrl, vmwTimestamp, vmwEventName }
   STATUS current
   DESCRIPTION
      "Host datastores changed"
   ::= { vmwVRNIEvents 20059}

vmwVMDatastoreChangeEvent NOTIFICATION-TYPE
   OBJECTS { vmwEventSeverity, vmwAffectedObject, vmwOperatorDesc, vmwVrniUrl, vmwTimestamp, vmwEventName }
   STATUS current
   DESCRIPTION
      "VM datastores changed"
   ::= { vmwVRNIEvents 20060}

vmwVMSnapshotChangeEvent NOTIFICATION-TYPE
   OBJECTS { vmwEventSeverity, vmwAffectedObject, vmwOperatorDesc, vmwVrniUrl, vmwTimestamp, vmwEventName }
   STATUS current
   DESCRIPTION
      "VM snapshot changed"
   ::= { vmwVRNIEvents 20061}

vmwVMVirtualDiskChangeEvent NOTIFICATION-TYPE
   OBJECTS { vmwEventSeverity, vmwAffectedObject, vmwOperatorDesc, vmwVrniUrl, vmwTimestamp, vmwEventName }
   STATUS current
   DESCRIPTION
      "Virtual disk migrated"
   ::= { vmwVRNIEvents 20062}

vmwIPSetDefinitionMismatchEvent NOTIFICATION-TYPE
   OBJECTS { vmwEventSeverity, vmwAffectedObject, vmwOperatorDesc, vmwVrniUrl, vmwTimestamp, vmwEventName }
   STATUS current
   DESCRIPTION
      "IPSET Definition Mismatch Event"
   ::= { vmwVRNIEvents 20063}

vmwSegmentMismatchEvent NOTIFICATION-TYPE
   OBJECTS { vmwEventSeverity, vmwAffectedObject, vmwOperatorDesc, vmwVrniUrl, vmwTimestamp, vmwEventName }
   STATUS current
   DESCRIPTION
      "Segment Mismatch Event"
   ::= { vmwVRNIEvents 20064}

vmwVtepEvent NOTIFICATION-TYPE
   OBJECTS { vmwEventSeverity, vmwAffectedObject, vmwOperatorDesc, vmwVrniUrl, vmwTimestamp, vmwEventName }
   STATUS current
   DESCRIPTION
      "Vtep Event"
   ::= { vmwVRNIEvents 20065}

vmwVtepConfigurationFaultEvent NOTIFICATION-TYPE
   OBJECTS { vmwEventSeverity, vmwAffectedObject, vmwOperatorDesc, vmwVrniUrl, vmwTimestamp, vmwEventName }
   STATUS current
   DESCRIPTION
      "Vtep Configuration Fault Event"
   ::= { vmwVRNIEvents 20066}

vmwVtepSubnetMismatchEvent NOTIFICATION-TYPE
   OBJECTS { vmwEventSeverity, vmwAffectedObject, vmwOperatorDesc, vmwVrniUrl, vmwTimestamp, vmwEventName }
   STATUS current
   DESCRIPTION
      "Vtep Subnet Mismatch Event"
   ::= { vmwVRNIEvents 20068}

vmwVtepCountMismatchEvent NOTIFICATION-TYPE
   OBJECTS { vmwEventSeverity, vmwAffectedObject, vmwOperatorDesc, vmwVrniUrl, vmwTimestamp, vmwEventName }
   STATUS current
   DESCRIPTION
      "Vtep Count Mismatch Event"
   ::= { vmwVRNIEvents 20069}

vmwDLRNetworksNotReachableEvent NOTIFICATION-TYPE
   OBJECTS { vmwEventSeverity, vmwAffectedObject, vmwOperatorDesc, vmwVrniUrl, vmwTimestamp, vmwEventName }
   STATUS current
   DESCRIPTION
      "DLR Routing event"
   ::= { vmwVRNIEvents 20067}

vmwEdgeNetworksNotReachableEvent NOTIFICATION-TYPE
   OBJECTS { vmwEventSeverity, vmwAffectedObject, vmwOperatorDesc, vmwVrniUrl, vmwTimestamp, vmwEventName }
   STATUS current
   DESCRIPTION
      "Edge Routing event"
   ::= { vmwVRNIEvents 20070}

vmwNiInfraChangeEvent NOTIFICATION-TYPE
   OBJECTS { vmwEventSeverity, vmwAffectedObject, vmwOperatorDesc, vmwVrniUrl, vmwTimestamp, vmwEventName }
   STATUS current
   DESCRIPTION
      "NI Infra Change"
   ::= { vmwVRNIEvents 20089}

vmwDataSourceEnabledChangeEvent NOTIFICATION-TYPE
   OBJECTS { vmwEventSeverity, vmwAffectedObject, vmwOperatorDesc, vmwVrniUrl, vmwTimestamp, vmwEventName }
   STATUS current
   DESCRIPTION
      "Data Source Enabled"
   ::= { vmwVRNIEvents 20090}

vmwDataSourceDisabledChangeEvent NOTIFICATION-TYPE
   OBJECTS { vmwEventSeverity, vmwAffectedObject, vmwOperatorDesc, vmwVrniUrl, vmwTimestamp, vmwEventName }
   STATUS current
   DESCRIPTION
      "Data Source Disabled"
   ::= { vmwVRNIEvents 20091}

vmwDataSourceCreatedEvent NOTIFICATION-TYPE
   OBJECTS { vmwEventSeverity, vmwAffectedObject, vmwOperatorDesc, vmwVrniUrl, vmwTimestamp, vmwEventName }
   STATUS current
   DESCRIPTION
      "Data Source Created"
   ::= { vmwVRNIEvents 20092}

vmwPlatformCpuCoreChangeEvent NOTIFICATION-TYPE
   OBJECTS { vmwEventSeverity, vmwAffectedObject, vmwOperatorDesc, vmwVrniUrl, vmwTimestamp, vmwEventName }
   STATUS current
   DESCRIPTION
      "Platform CPU Change Event"
   ::= { vmwVRNIEvents 20093}

vmwPlatformDiskChangeEvent NOTIFICATION-TYPE
   OBJECTS { vmwEventSeverity, vmwAffectedObject, vmwOperatorDesc, vmwVrniUrl, vmwTimestamp, vmwEventName }
   STATUS current
   DESCRIPTION
      "Platform Disk Change Event"
   ::= { vmwVRNIEvents 20094}

vmwPlatformMemoryChangeEvent NOTIFICATION-TYPE
   OBJECTS { vmwEventSeverity, vmwAffectedObject, vmwOperatorDesc, vmwVrniUrl, vmwTimestamp, vmwEventName }
   STATUS current
   DESCRIPTION
      "Platform Memory Change Event"
   ::= { vmwVRNIEvents 20095}

vmwPlatformRebootedEvent NOTIFICATION-TYPE
   OBJECTS { vmwEventSeverity, vmwAffectedObject, vmwOperatorDesc, vmwVrniUrl, vmwTimestamp, vmwEventName }
   STATUS current
   DESCRIPTION
      "Platform Reboot Change Event"
   ::= { vmwVRNIEvents 20096}

vmwProxyCpuCoreChangeEvent NOTIFICATION-TYPE
   OBJECTS { vmwEventSeverity, vmwAffectedObject, vmwOperatorDesc, vmwVrniUrl, vmwTimestamp, vmwEventName }
   STATUS current
   DESCRIPTION
      "Collector CPU Change Event"
   ::= { vmwVRNIEvents 20097}

vmwProxyDiskChangeEvent NOTIFICATION-TYPE
   OBJECTS { vmwEventSeverity, vmwAffectedObject, vmwOperatorDesc, vmwVrniUrl, vmwTimestamp, vmwEventName }
   STATUS current
   DESCRIPTION
      "Collector Disk Change Event"
   ::= { vmwVRNIEvents 20098}

vmwProxyMemoryChangeEvent NOTIFICATION-TYPE
   OBJECTS { vmwEventSeverity, vmwAffectedObject, vmwOperatorDesc, vmwVrniUrl, vmwTimestamp, vmwEventName }
   STATUS current
   DESCRIPTION
      "Collector Memory Change Event"
   ::= { vmwVRNIEvents 20099}

vmwProxyRebootedEvent NOTIFICATION-TYPE
   OBJECTS { vmwEventSeverity, vmwAffectedObject, vmwOperatorDesc, vmwVrniUrl, vmwTimestamp, vmwEventName }
   STATUS current
   DESCRIPTION
      "Collector Reboot Change Event"
   ::= { vmwVRNIEvents 20100}

vmwNIClusterChangeEvent NOTIFICATION-TYPE
   OBJECTS { vmwEventSeverity, vmwAffectedObject, vmwOperatorDesc, vmwVrniUrl, vmwTimestamp, vmwEventName }
   STATUS current
   DESCRIPTION
      "Cluster Change Event"
   ::= { vmwVRNIEvents 20101}

vmwNISystemProxyChangeEvent NOTIFICATION-TYPE
   OBJECTS { vmwEventSeverity, vmwAffectedObject, vmwOperatorDesc, vmwVrniUrl, vmwTimestamp, vmwEventName }
   STATUS current
   DESCRIPTION
      "System Proxy Change Event"
   ::= { vmwVRNIEvents 20102}

vmwNIClusterCreateEvent NOTIFICATION-TYPE
   OBJECTS { vmwEventSeverity, vmwAffectedObject, vmwOperatorDesc, vmwVrniUrl, vmwTimestamp, vmwEventName }
   STATUS current
   DESCRIPTION
      "Cluster Create Event"
   ::= { vmwVRNIEvents 20103}

vmwThresholdExceededEventCpuReady NOTIFICATION-TYPE
   OBJECTS { vmwEventSeverity, vmwAffectedObject, vmwOperatorDesc, vmwVrniUrl, vmwTimestamp, vmwEventName }
   STATUS current
   DESCRIPTION
      "Threshold Exceeded Cpu Ready"
   ::= { vmwVRNIEvents 30001}

vmwThresholdExceededEventCpuCoStop NOTIFICATION-TYPE
   OBJECTS { vmwEventSeverity, vmwAffectedObject, vmwOperatorDesc, vmwVrniUrl, vmwTimestamp, vmwEventName }
   STATUS current
   DESCRIPTION
      "Threshold Exceeded Cpu Co Stop"
   ::= { vmwVRNIEvents 30002}

vmwThresholdExceededEventDiskCommandAbortRule NOTIFICATION-TYPE
   OBJECTS { vmwEventSeverity, vmwAffectedObject, vmwOperatorDesc, vmwVrniUrl, vmwTimestamp, vmwEventName }
   STATUS current
   DESCRIPTION
      "Threshold Exceeded Disk Command Abort Rule"
   ::= { vmwVRNIEvents 30003}

vmwThresholdExceededEventIODeviceLatencyRule NOTIFICATION-TYPE
   OBJECTS { vmwEventSeverity, vmwAffectedObject, vmwOperatorDesc, vmwVrniUrl, vmwTimestamp, vmwEventName }
   STATUS current
   DESCRIPTION
      "Threshold Exceeded IO Device Latency Rule"
   ::= { vmwVRNIEvents 30004}

vmwThresholdExceededEventIOKernelLatencyRule NOTIFICATION-TYPE
   OBJECTS { vmwEventSeverity, vmwAffectedObject, vmwOperatorDesc, vmwVrniUrl, vmwTimestamp, vmwEventName }
   STATUS current
   DESCRIPTION
      "Threshold Exceeded IO Kernel Latency Rule"
   ::= { vmwVRNIEvents 30005}

vmwThresholdExceededEventMemorySwapInRule NOTIFICATION-TYPE
   OBJECTS { vmwEventSeverity, vmwAffectedObject, vmwOperatorDesc, vmwVrniUrl, vmwTimestamp, vmwEventName }
   STATUS current
   DESCRIPTION
      "Threshold Exceeded Memory Swap In Rule"
   ::= { vmwVRNIEvents 30006}

vmwThresholdExceededEventMemorySwapOutRule NOTIFICATION-TYPE
   OBJECTS { vmwEventSeverity, vmwAffectedObject, vmwOperatorDesc, vmwVrniUrl, vmwTimestamp, vmwEventName }
   STATUS current
   DESCRIPTION
      "Threshold Exceeded Memory Swap Out Rule"
   ::= { vmwVRNIEvents 30007}

vmwThresholdExceededEventNetworkRxDropRule NOTIFICATION-TYPE
   OBJECTS { vmwEventSeverity, vmwAffectedObject, vmwOperatorDesc, vmwVrniUrl, vmwTimestamp, vmwEventName }
   STATUS current
   DESCRIPTION
      "Threshold Exceeded Memory Rx Drop Rule"
   ::= { vmwVRNIEvents 30008}

vmwThresholdExceededEventNetworkTxDropRule NOTIFICATION-TYPE
   OBJECTS { vmwEventSeverity, vmwAffectedObject, vmwOperatorDesc, vmwVrniUrl, vmwTimestamp, vmwEventName }
   STATUS current
   DESCRIPTION
      "Threshold Exceeded Memory Tx Drop Rule"
   ::= { vmwVRNIEvents 30009}

vmwAWSRegionSGLimitEvent NOTIFICATION-TYPE
   OBJECTS { vmwEventSeverity, vmwAffectedObject, vmwOperatorDesc, vmwVrniUrl, vmwTimestamp, vmwEventName }
   STATUS current
   DESCRIPTION
      "AWS Region Security Group count near threshold."
   ::= { vmwVRNIEvents 30010}

vmwAWSVPCSGLimitEvent NOTIFICATION-TYPE
   OBJECTS { vmwEventSeverity, vmwAffectedObject, vmwOperatorDesc, vmwVrniUrl, vmwTimestamp, vmwEventName }
   STATUS current
   DESCRIPTION
      "AWS VPC Security Group count near threshold."
   ::= { vmwVRNIEvents 30011}

vmwAWSSGInboundRuleLimitEvent NOTIFICATION-TYPE
   OBJECTS { vmwEventSeverity, vmwAffectedObject, vmwOperatorDesc, vmwVrniUrl, vmwTimestamp, vmwEventName }
   STATUS current
   DESCRIPTION
      "AWS Security Group Inbound Rule count near threshold."
   ::= { vmwVRNIEvents 30012}

vmwAWSSGOutboundRuleLimitEvent NOTIFICATION-TYPE
   OBJECTS { vmwEventSeverity, vmwAffectedObject, vmwOperatorDesc, vmwVrniUrl, vmwTimestamp, vmwEventName }
   STATUS current
   DESCRIPTION
      "AWS Security Group Outbound Rule count near threshold."
   ::= { vmwVRNIEvents 30013}

vmwAWSInterfaceSGLimitEvent NOTIFICATION-TYPE
   OBJECTS { vmwEventSeverity, vmwAffectedObject, vmwOperatorDesc, vmwVrniUrl, vmwTimestamp, vmwEventName }
   STATUS current
   DESCRIPTION
      "AWS VPC Security Group count near threshold."
   ::= { vmwVRNIEvents 30014}

vmwPacketDropEvent NOTIFICATION-TYPE
   OBJECTS { vmwEventSeverity, vmwAffectedObject, vmwOperatorDesc, vmwVrniUrl, vmwTimestamp, vmwEventName }
   STATUS current
   DESCRIPTION
      "Packet Drop Event"
   ::= { vmwVRNIEvents 30100}

vmwSwitchPortPacketDropEvent NOTIFICATION-TYPE
   OBJECTS { vmwEventSeverity, vmwAffectedObject, vmwOperatorDesc, vmwVrniUrl, vmwTimestamp, vmwEventName }
   STATUS current
   DESCRIPTION
      "Switch Port Packet Drop"
   ::= { vmwVRNIEvents 30101}

vmwRouterInterfacePacketDropEvent NOTIFICATION-TYPE
   OBJECTS { vmwEventSeverity, vmwAffectedObject, vmwOperatorDesc, vmwVrniUrl, vmwTimestamp, vmwEventName }
   STATUS current
   DESCRIPTION
      "Router Interface Packet Drop"
   ::= { vmwVRNIEvents 30102}

vmwVnicPacketDropEvent NOTIFICATION-TYPE
   OBJECTS { vmwEventSeverity, vmwAffectedObject, vmwOperatorDesc, vmwVrniUrl, vmwTimestamp, vmwEventName }
   STATUS current
   DESCRIPTION
      "Vnic Packet Drop"
   ::= { vmwVRNIEvents 30103}

vmwVTEPUnderlayPacketDropEvent NOTIFICATION-TYPE
   OBJECTS { vmwEventSeverity, vmwAffectedObject, vmwOperatorDesc, vmwVrniUrl, vmwTimestamp, vmwEventName }
   STATUS current
   DESCRIPTION
      "VTEP Underlay Packet Drop"
   ::= { vmwVRNIEvents 30104}

vmwPnicUnderlyingSwitchPortPacketDropEvent NOTIFICATION-TYPE
   OBJECTS { vmwEventSeverity, vmwAffectedObject, vmwOperatorDesc, vmwVrniUrl, vmwTimestamp, vmwEventName }
   STATUS current
   DESCRIPTION
      "PNIC Underlying Switch Port Packet Drop"
   ::= { vmwVRNIEvents 30105}

vmwDevicePacketDropEvent NOTIFICATION-TYPE
   OBJECTS { vmwEventSeverity, vmwAffectedObject, vmwOperatorDesc, vmwVrniUrl, vmwTimestamp, vmwEventName }
   STATUS current
   DESCRIPTION
      "Device Packet Drop"
   ::= { vmwVRNIEvents 30106}

vmwThresholdExceededEventDatastoreFreeSpaceWarning NOTIFICATION-TYPE
   OBJECTS { vmwEventSeverity, vmwAffectedObject, vmwOperatorDesc, vmwVrniUrl, vmwTimestamp, vmwEventName }
   STATUS current
   DESCRIPTION
      "ThresholdExceededEventDatastoreFreeSpaceWarning"
   ::= { vmwVRNIEvents 30203}

vmwThresholdExceededEventDatastoreFreeSpaceCritical NOTIFICATION-TYPE
   OBJECTS { vmwEventSeverity, vmwAffectedObject, vmwOperatorDesc, vmwVrniUrl, vmwTimestamp, vmwEventName }
   STATUS current
   DESCRIPTION
      "ThresholdExceededEventDatastoreFreeSpaceCritical"
   ::= { vmwVRNIEvents 30204}

vmwThresholdExceededEventDatastoreReadLatency NOTIFICATION-TYPE
   OBJECTS { vmwEventSeverity, vmwAffectedObject, vmwOperatorDesc, vmwVrniUrl, vmwTimestamp, vmwEventName }
   STATUS current
   DESCRIPTION
      "ThresholdExceededEventDatastoreReadLatency"
   ::= { vmwVRNIEvents 30205}

vmwThresholdExceededEventDatastoreWriteLatency NOTIFICATION-TYPE
   OBJECTS { vmwEventSeverity, vmwAffectedObject, vmwOperatorDesc, vmwVrniUrl, vmwTimestamp, vmwEventName }
   STATUS current
   DESCRIPTION
      "ThresholdExceededEventDatastoreWriteLatency"
   ::= { vmwVRNIEvents 30206}

vmwDistributedFirewallApplyHostEvent NOTIFICATION-TYPE
   OBJECTS { vmwEventSeverity, vmwAffectedObject, vmwOperatorDesc, vmwVrniUrl, vmwTimestamp, vmwEventName }
   STATUS current
   DESCRIPTION
      "Distributed Firewall Apply Host Event"
   ::= { vmwVRNIEvents 35001}

vmwDistributedFirewallApplyVMEvent NOTIFICATION-TYPE
   OBJECTS { vmwEventSeverity, vmwAffectedObject, vmwOperatorDesc, vmwVrniUrl, vmwTimestamp, vmwEventName }
   STATUS current
   DESCRIPTION
      "Distributed Firewall Apply VM Event"
   ::= { vmwVRNIEvents 35002}

vmwNsxEvent NOTIFICATION-TYPE
   OBJECTS { vmwEventSeverity, vmwAffectedObject, vmwOperatorDesc, vmwVrniUrl, vmwTimestamp, vmwEventName }
   STATUS current
   DESCRIPTION
      "NSX Event"
   ::= { vmwVRNIEvents 35003}

vmwFeatureImpactedEvent NOTIFICATION-TYPE
   OBJECTS { vmwEventSeverity, vmwAffectedObject, vmwOperatorDesc, vmwVrniUrl, vmwTimestamp, vmwEventName }
   STATUS current
   DESCRIPTION
      "Feature Impacted Event"
   ::= { vmwVRNIEvents 35004}

vmwClusterFeatureVersionMismatchEvent NOTIFICATION-TYPE
   OBJECTS { vmwEventSeverity, vmwAffectedObject, vmwOperatorDesc, vmwVrniUrl, vmwTimestamp, vmwEventName }
   STATUS current
   DESCRIPTION
      "Cluster Feature Mismatch Event"
   ::= { vmwVRNIEvents 36022}

vmwHostFeatureVersionMismatchEvent NOTIFICATION-TYPE
   OBJECTS { vmwEventSeverity, vmwAffectedObject, vmwOperatorDesc, vmwVrniUrl, vmwTimestamp, vmwEventName }
   STATUS current
   DESCRIPTION
      "Host Feature Mismatch Event"
   ::= { vmwVRNIEvents 36023}

vmwFeatureVersionMismatchEvent NOTIFICATION-TYPE
   OBJECTS { vmwEventSeverity, vmwAffectedObject, vmwOperatorDesc, vmwVrniUrl, vmwTimestamp, vmwEventName }
   STATUS current
   DESCRIPTION
      "Feature Version Mismatch Event"
   ::= { vmwVRNIEvents 36024}

vmwHostFeatureEnabledMismatchEvent NOTIFICATION-TYPE
   OBJECTS { vmwEventSeverity, vmwAffectedObject, vmwOperatorDesc, vmwVrniUrl, vmwTimestamp, vmwEventName }
   STATUS current
   DESCRIPTION
      "Feature Enabled Mismatch Event"
   ::= { vmwVRNIEvents 36025}

vmwHostFeatureInstalledMismatchEvent NOTIFICATION-TYPE
   OBJECTS { vmwEventSeverity, vmwAffectedObject, vmwOperatorDesc, vmwVrniUrl, vmwTimestamp, vmwEventName }
   STATUS current
   DESCRIPTION
      "Feature Installed Mismatch Event"
   ::= { vmwVRNIEvents 36026}

vmwHostVtepNotFoundEvent NOTIFICATION-TYPE
   OBJECTS { vmwEventSeverity, vmwAffectedObject, vmwOperatorDesc, vmwVrniUrl, vmwTimestamp, vmwEventName }
   STATUS current
   DESCRIPTION
      "Host Vtep Not Found Event"
   ::= { vmwVRNIEvents 36027}

vmwHostVtepDisconnectedEvent NOTIFICATION-TYPE
   OBJECTS { vmwEventSeverity, vmwAffectedObject, vmwOperatorDesc, vmwVrniUrl, vmwTimestamp, vmwEventName }
   STATUS current
   DESCRIPTION
      "Host Vtep Disconnected Event"
   ::= { vmwVRNIEvents 36028}

vmwHostVtepEvent NOTIFICATION-TYPE
   OBJECTS { vmwEventSeverity, vmwAffectedObject, vmwOperatorDesc, vmwVrniUrl, vmwTimestamp, vmwEventName }
   STATUS current
   DESCRIPTION
      "Host Vtep Event"
   ::= { vmwVRNIEvents 36029}

vmwClusterHostsVtepMTUMismatchEvent NOTIFICATION-TYPE
   OBJECTS { vmwEventSeverity, vmwAffectedObject, vmwOperatorDesc, vmwVrniUrl, vmwTimestamp, vmwEventName }
   STATUS current
   DESCRIPTION
      "Host Vtep Mtu Mismatch Event"
   ::= { vmwVRNIEvents 36030}

vmwFeatureUnhealthyEvent NOTIFICATION-TYPE
   OBJECTS { vmwEventSeverity, vmwAffectedObject, vmwOperatorDesc, vmwVrniUrl, vmwTimestamp, vmwEventName }
   STATUS current
   DESCRIPTION
      "Feature Health Event"
   ::= { vmwVRNIEvents 36031}

vmwEdgeHANotConfiguredEvent NOTIFICATION-TYPE
   OBJECTS { vmwEventSeverity, vmwAffectedObject, vmwOperatorDesc, vmwVrniUrl, vmwTimestamp, vmwEventName }
   STATUS current
   DESCRIPTION
      "NSX Edge High Availability is not enabled Event"
   ::= { vmwVRNIEvents 36032}

vmwEdgeInterfacesDownEvent NOTIFICATION-TYPE
   OBJECTS { vmwEventSeverity, vmwAffectedObject, vmwOperatorDesc, vmwVrniUrl, vmwTimestamp, vmwEventName }
   STATUS current
   DESCRIPTION
      "One or More NSX Edge Interfaces are down Event"
   ::= { vmwVRNIEvents 36033}

vmwModuleUnhealthyEvent NOTIFICATION-TYPE
   OBJECTS { vmwEventSeverity, vmwAffectedObject, vmwOperatorDesc, vmwVrniUrl, vmwTimestamp, vmwEventName }
   STATUS current
   DESCRIPTION
      "Module Unhealthy Event"
   ::= { vmwVRNIEvents 36041}

vmwModuleNotLoadedEvent NOTIFICATION-TYPE
   OBJECTS { vmwEventSeverity, vmwAffectedObject, vmwOperatorDesc, vmwVrniUrl, vmwTimestamp, vmwEventName }
   STATUS current
   DESCRIPTION
      "Module Not Loaded Event"
   ::= { vmwVRNIEvents 36042}

vmwModuleNetworkConnectionFailureEvent NOTIFICATION-TYPE
   OBJECTS { vmwEventSeverity, vmwAffectedObject, vmwOperatorDesc, vmwVrniUrl, vmwTimestamp, vmwEventName }
   STATUS current
   DESCRIPTION
      "Module Network Connection Failure Event"
   ::= { vmwVRNIEvents 36043}

vmwHostNetworkControlPlaneMismatchEvent NOTIFICATION-TYPE
   OBJECTS { vmwEventSeverity, vmwAffectedObject, vmwOperatorDesc, vmwVrniUrl, vmwTimestamp, vmwEventName }
   STATUS current
   DESCRIPTION
      "Control Plane Network Mismatch Event"
   ::= { vmwVRNIEvents 36044}

vmwHostNetworkControlPlaneConnectionFailureEvent NOTIFICATION-TYPE
   OBJECTS { vmwEventSeverity, vmwAffectedObject, vmwOperatorDesc, vmwVrniUrl, vmwTimestamp, vmwEventName }
   STATUS current
   DESCRIPTION
      "Control Plane Network Connection Failure Event"
   ::= { vmwVRNIEvents 36045}

vmwHostNetworkControlPlaneNotSyncedEvent NOTIFICATION-TYPE
   OBJECTS { vmwEventSeverity, vmwAffectedObject, vmwOperatorDesc, vmwVrniUrl, vmwTimestamp, vmwEventName }
   STATUS current
   DESCRIPTION
      "Host Control Plane Sync Failure Event"
   ::= { vmwVRNIEvents 36046}

vmwNSXControllerClusterMajorityEvent NOTIFICATION-TYPE
   OBJECTS { vmwEventSeverity, vmwAffectedObject, vmwOperatorDesc, vmwVrniUrl, vmwTimestamp, vmwEventName }
   STATUS current
   DESCRIPTION
      "NSX Controller Cluster Majority Event"
   ::= { vmwVRNIEvents 36047}

vmwNSXControllersVMOnSameHostEvent NOTIFICATION-TYPE
   OBJECTS { vmwEventSeverity, vmwAffectedObject, vmwOperatorDesc, vmwVrniUrl, vmwTimestamp, vmwEventName }
   STATUS current
   DESCRIPTION
      "NSX Controllers VM On Same Host Event"
   ::= { vmwVRNIEvents 36048}

vmwVxLanRangeExhaustEvent NOTIFICATION-TYPE
   OBJECTS { vmwEventSeverity, vmwAffectedObject, vmwOperatorDesc, vmwVrniUrl, vmwTimestamp, vmwEventName }
   STATUS current
   DESCRIPTION
      "Vxlan range exhaust  Event"
   ::= { vmwVRNIEvents 36049}

vmwNSXFirewallDefaultAllowAllRulesEvent NOTIFICATION-TYPE
   OBJECTS { vmwEventSeverity, vmwAffectedObject, vmwOperatorDesc, vmwVrniUrl, vmwTimestamp, vmwEventName }
   STATUS current
   DESCRIPTION
      "NSX Firewall Allow All Rules Event"
   ::= { vmwVRNIEvents 36050}

vmwLogicalRouterNoUplinkEvent NOTIFICATION-TYPE
   OBJECTS { vmwEventSeverity, vmwAffectedObject, vmwOperatorDesc, vmwVrniUrl, vmwTimestamp, vmwEventName }
   STATUS current
   DESCRIPTION
      "Logical Router does not have an uplink interface configured Event"
   ::= { vmwVRNIEvents 36051}

vmwEdgeNotHAEvent NOTIFICATION-TYPE
   OBJECTS { vmwEventSeverity, vmwAffectedObject, vmwOperatorDesc, vmwVrniUrl, vmwTimestamp, vmwEventName }
   STATUS current
   DESCRIPTION
      "NSX Edge not Highly Available Event"
   ::= { vmwVRNIEvents 36052}

vmwEdgeNotDeployedEvent NOTIFICATION-TYPE
   OBJECTS { vmwEventSeverity, vmwAffectedObject, vmwOperatorDesc, vmwVrniUrl, vmwTimestamp, vmwEventName }
   STATUS current
   DESCRIPTION
      "NSX Edge not deployed Event"
   ::= { vmwVRNIEvents 36053}

vmwEcmpIsEnabledAndStatefulServicesAreUpEvent NOTIFICATION-TYPE
   OBJECTS { vmwEventSeverity, vmwAffectedObject, vmwOperatorDesc, vmwVrniUrl, vmwTimestamp, vmwEventName }
   STATUS current
   DESCRIPTION
      "NSX Edge Running with both ECMP and Stateful Edge Services Event"
   ::= { vmwVRNIEvents 36054}

vmwLogicalRouterDeployedOnEcmpEdgeHostEvent NOTIFICATION-TYPE
   OBJECTS { vmwEventSeverity, vmwAffectedObject, vmwOperatorDesc, vmwVrniUrl, vmwTimestamp, vmwEventName }
   STATUS current
   DESCRIPTION
      "Logical Router and ECMP Edge on Same Host Event"
   ::= { vmwVRNIEvents 36055}

vmwEdgeMissingInterfaceOSPFAreaMappingEvent NOTIFICATION-TYPE
   OBJECTS { vmwEventSeverity, vmwAffectedObject, vmwOperatorDesc, vmwVrniUrl, vmwTimestamp, vmwEventName }
   STATUS current
   DESCRIPTION
      "NSX Edge Interface to OSPF Area Mapping Missing Event"
   ::= { vmwVRNIEvents 36056}

vmwOspfInsecureAuthRouterEvent NOTIFICATION-TYPE
   OBJECTS { vmwEventSeverity, vmwAffectedObject, vmwOperatorDesc, vmwVrniUrl, vmwTimestamp, vmwEventName }
   STATUS current
   DESCRIPTION
      "One or more OSPF areas on the NSX Edge are using insecure authentication Event"
   ::= { vmwVRNIEvents 36057}

vmwNSXControllersDeployedCountEvent NOTIFICATION-TYPE
   OBJECTS { vmwEventSeverity, vmwAffectedObject, vmwOperatorDesc, vmwVrniUrl, vmwTimestamp, vmwEventName }
   STATUS current
   DESCRIPTION
      "NSX Controller count  Event"
   ::= { vmwVRNIEvents 36058}

vmwNSXControllerNotActiveCountEvent NOTIFICATION-TYPE
   OBJECTS { vmwEventSeverity, vmwAffectedObject, vmwOperatorDesc, vmwVrniUrl, vmwTimestamp, vmwEventName }
   STATUS current
   DESCRIPTION
      "NSX Controller Not Active  Event"
   ::= { vmwVRNIEvents 36059}

vmwNSXControllerEvent NOTIFICATION-TYPE
   OBJECTS { vmwEventSeverity, vmwAffectedObject, vmwOperatorDesc, vmwVrniUrl, vmwTimestamp, vmwEventName }
   STATUS current
   DESCRIPTION
      "NSX Controller Event"
   ::= { vmwVRNIEvents 36060}

vmwNSXEcmpEdgeDownEvent NOTIFICATION-TYPE
   OBJECTS { vmwEventSeverity, vmwAffectedObject, vmwOperatorDesc, vmwVrniUrl, vmwTimestamp, vmwEventName }
   STATUS current
   DESCRIPTION
      "One or more NSX Edges in the ECMP Cluster are currently down"
   ::= { vmwVRNIEvents 36061}

vmwNSXMajorityEcmpEdgesDownEvent NOTIFICATION-TYPE
   OBJECTS { vmwEventSeverity, vmwAffectedObject, vmwOperatorDesc, vmwVrniUrl, vmwTimestamp, vmwEventName }
   STATUS current
   DESCRIPTION
      "The majority of NSX Edges in the ECMP Cluster are currently down"
   ::= { vmwVRNIEvents 36062}

vmwNSXAllEcmpEdgesDownEvent NOTIFICATION-TYPE
   OBJECTS { vmwEventSeverity, vmwAffectedObject, vmwOperatorDesc, vmwVrniUrl, vmwTimestamp, vmwEventName }
   STATUS current
   DESCRIPTION
      "All NSX Edges in the ECMP Cluster are currently down"
   ::= { vmwVRNIEvents 36063}

vmwNSXEdgeMtuMismatchEvent NOTIFICATION-TYPE
   OBJECTS { vmwEventSeverity, vmwAffectedObject, vmwOperatorDesc, vmwVrniUrl, vmwTimestamp, vmwEventName }
   STATUS current
   DESCRIPTION
      "The MTU configured on one or more interfaces on the Edge does not match the MTU on the next hop router"
   ::= { vmwVRNIEvents 36064}

vmwNSXEdgeSplitBrainEvent NOTIFICATION-TYPE
   OBJECTS { vmwEventSeverity, vmwAffectedObject, vmwOperatorDesc, vmwVrniUrl, vmwTimestamp, vmwEventName }
   STATUS current
   DESCRIPTION
      "Both VMs of Edge HA are in active state"
   ::= { vmwVRNIEvents 36065}

vmwVirtualDistributedRoutingEvent NOTIFICATION-TYPE
   OBJECTS { vmwEventSeverity, vmwAffectedObject, vmwOperatorDesc, vmwVrniUrl, vmwTimestamp, vmwEventName }
   STATUS current
   DESCRIPTION
      "VDR Port Unset Event"
   ::= { vmwVRNIEvents 36066}

vmwNSXComponentEvent NOTIFICATION-TYPE
   OBJECTS { vmwEventSeverity, vmwAffectedObject, vmwOperatorDesc, vmwVrniUrl, vmwTimestamp, vmwEventName }
   STATUS current
   DESCRIPTION
      "NSX Service not running event"
   ::= { vmwVRNIEvents 35221}

vmwNSXBackupEvent NOTIFICATION-TYPE
   OBJECTS { vmwEventSeverity, vmwAffectedObject, vmwOperatorDesc, vmwVrniUrl, vmwTimestamp, vmwEventName }
   STATUS current
   DESCRIPTION
      "NSX Backup not configured"
   ::= { vmwVRNIEvents 35222}

vmwNSXBackupAuditLogExcludedEvent NOTIFICATION-TYPE
   OBJECTS { vmwEventSeverity, vmwAffectedObject, vmwOperatorDesc, vmwVrniUrl, vmwTimestamp, vmwEventName }
   STATUS current
   DESCRIPTION
      "Audit Log excluded from NSX Backup"
   ::= { vmwVRNIEvents 35223}

vmwNSXUnsecureBackupEvent NOTIFICATION-TYPE
   OBJECTS { vmwEventSeverity, vmwAffectedObject, vmwOperatorDesc, vmwVrniUrl, vmwTimestamp, vmwEventName }
   STATUS current
   DESCRIPTION
      "NSX Backups not using secure FTP"
   ::= { vmwVRNIEvents 35224}

vmwNSXBackupSystemEventsExcludedEvent NOTIFICATION-TYPE
   OBJECTS { vmwEventSeverity, vmwAffectedObject, vmwOperatorDesc, vmwVrniUrl, vmwTimestamp, vmwEventName }
   STATUS current
   DESCRIPTION
      "System Event excluded from NSX Backup"
   ::= { vmwVRNIEvents 35225}

vmwNSXBackupNotScheduledEvent NOTIFICATION-TYPE
   OBJECTS { vmwEventSeverity, vmwAffectedObject, vmwOperatorDesc, vmwVrniUrl, vmwTimestamp, vmwEventName }
   STATUS current
   DESCRIPTION
      "Scheduled backups are not enabled"
   ::= { vmwVRNIEvents 35226}

vmwNSXBackupNotRecordedEvent NOTIFICATION-TYPE
   OBJECTS { vmwEventSeverity, vmwAffectedObject, vmwOperatorDesc, vmwVrniUrl, vmwTimestamp, vmwEventName }
   STATUS current
   DESCRIPTION
      "No backup of the environment has been recorded"
   ::= { vmwVRNIEvents 35227}

vmwNSXNtpServerEvent NOTIFICATION-TYPE
   OBJECTS { vmwEventSeverity, vmwAffectedObject, vmwOperatorDesc, vmwVrniUrl, vmwTimestamp, vmwEventName }
   STATUS current
   DESCRIPTION
      "NTP Server not configured"
   ::= { vmwVRNIEvents 35228}

vmwNSXSysLogServerEvent NOTIFICATION-TYPE
   OBJECTS { vmwEventSeverity, vmwAffectedObject, vmwOperatorDesc, vmwVrniUrl, vmwTimestamp, vmwEventName }
   STATUS current
   DESCRIPTION
      "Syslog Server not configured"
   ::= { vmwVRNIEvents 35229}

vmwControllerSysLogServerEvent NOTIFICATION-TYPE
   OBJECTS { vmwEventSeverity, vmwAffectedObject, vmwOperatorDesc, vmwVrniUrl, vmwTimestamp, vmwEventName }
   STATUS current
   DESCRIPTION
      "Syslog Server not configured"
   ::= { vmwVRNIEvents 35230}

vmwNSXIpV6EnabledEvent NOTIFICATION-TYPE
   OBJECTS { vmwEventSeverity, vmwAffectedObject, vmwOperatorDesc, vmwVrniUrl, vmwTimestamp, vmwEventName }
   STATUS current
   DESCRIPTION
      "IPv6 is enabled for NSX Manager"
   ::= { vmwVRNIEvents 35231}

vmwNSXOspfNeighborDownEvent NOTIFICATION-TYPE
   OBJECTS { vmwEventSeverity, vmwAffectedObject, vmwOperatorDesc, vmwVrniUrl, vmwTimestamp, vmwEventName }
   STATUS current
   DESCRIPTION
      "One or more OSPF Neighbors down"
   ::= { vmwVRNIEvents 35232}

vmwGenericNSXSystemEvent NOTIFICATION-TYPE
   OBJECTS { vmwEventSeverity, vmwAffectedObject, vmwOperatorDesc, vmwVrniUrl, vmwTimestamp, vmwEventName }
   STATUS current
   DESCRIPTION
      "NSX System Event (Warning)"
   ::= { vmwVRNIEvents 70000}

vmwOtherCriticalNSXEvent NOTIFICATION-TYPE
   OBJECTS { vmwEventSeverity, vmwAffectedObject, vmwOperatorDesc, vmwVrniUrl, vmwTimestamp, vmwEventName }
   STATUS current
   DESCRIPTION
      "NSX System Event (Critical)"
   ::= { vmwVRNIEvents 71000}

vmwFilterConfigApplyOnHostFailedEvent NOTIFICATION-TYPE
   OBJECTS { vmwEventSeverity, vmwAffectedObject, vmwOperatorDesc, vmwVrniUrl, vmwTimestamp, vmwEventName }
   STATUS current
   DESCRIPTION
      "Filter Config Apply On Host Failed Event"
   ::= { vmwVRNIEvents 70001}

vmwRulesetLoadOnHostFailedEvent NOTIFICATION-TYPE
   OBJECTS { vmwEventSeverity, vmwAffectedObject, vmwOperatorDesc, vmwVrniUrl, vmwTimestamp, vmwEventName }
   STATUS current
   DESCRIPTION
      "Ruleset Load On Host Failed Event"
   ::= { vmwVRNIEvents 70002}

vmwConfigUpdateOnHostFailedEvent NOTIFICATION-TYPE
   OBJECTS { vmwEventSeverity, vmwAffectedObject, vmwOperatorDesc, vmwVrniUrl, vmwTimestamp, vmwEventName }
   STATUS current
   DESCRIPTION
      "Config Update On Host Failed Event"
   ::= { vmwVRNIEvents 70003}

vmwSpoofguardConfigUpdateOnHostFailedEvent NOTIFICATION-TYPE
   OBJECTS { vmwEventSeverity, vmwAffectedObject, vmwOperatorDesc, vmwVrniUrl, vmwTimestamp, vmwEventName }
   STATUS current
   DESCRIPTION
      "Spoofguard Config Update On Host Failed Event"
   ::= { vmwVRNIEvents 70004}

vmwApplyRuleToVnicFailedEvent NOTIFICATION-TYPE
   OBJECTS { vmwEventSeverity, vmwAffectedObject, vmwOperatorDesc, vmwVrniUrl, vmwTimestamp, vmwEventName }
   STATUS current
   DESCRIPTION
      "Apply Rule To Vnic Failed Event"
   ::= { vmwVRNIEvents 70005}

vmwContainerConfigUpdateOnVnicFailedEvent NOTIFICATION-TYPE
   OBJECTS { vmwEventSeverity, vmwAffectedObject, vmwOperatorDesc, vmwVrniUrl, vmwTimestamp, vmwEventName }
   STATUS current
   DESCRIPTION
      "Container Config Update On Vnic Failed Event"
   ::= { vmwVRNIEvents 70006}

vmwSpoofguardApplyToVnicFailedEvent NOTIFICATION-TYPE
   OBJECTS { vmwEventSeverity, vmwAffectedObject, vmwOperatorDesc, vmwVrniUrl, vmwTimestamp, vmwEventName }
   STATUS current
   DESCRIPTION
      "Spoofguard Apply To Vnic Failed Event"
   ::= { vmwVRNIEvents 70007}

vmwHostMessagingConfigurationFailedEvent NOTIFICATION-TYPE
   OBJECTS { vmwEventSeverity, vmwAffectedObject, vmwOperatorDesc, vmwVrniUrl, vmwTimestamp, vmwEventName }
   STATUS current
   DESCRIPTION
      "Host Messaging Configuration Failed Event"
   ::= { vmwVRNIEvents 70008}

vmwHostMessagingConnectionReconfigurationFailedEvent NOTIFICATION-TYPE
   OBJECTS { vmwEventSeverity, vmwAffectedObject, vmwOperatorDesc, vmwVrniUrl, vmwTimestamp, vmwEventName }
   STATUS current
   DESCRIPTION
      "Host Messaging Connection Reconfiguration Failed Event"
   ::= { vmwVRNIEvents 70009}

vmwHostMessagingConfigurationFailedNotificationSkippedEvent NOTIFICATION-TYPE
   OBJECTS { vmwEventSeverity, vmwAffectedObject, vmwOperatorDesc, vmwVrniUrl, vmwTimestamp, vmwEventName }
   STATUS current
   DESCRIPTION
      "Host Messaging Configuration Failed Notification Skipped Event"
   ::= { vmwVRNIEvents 70010}

vmwHostMessagingInfrastructureDownEvent NOTIFICATION-TYPE
   OBJECTS { vmwEventSeverity, vmwAffectedObject, vmwOperatorDesc, vmwVrniUrl, vmwTimestamp, vmwEventName }
   STATUS current
   DESCRIPTION
      "Host Messaging Infrastructure Down Event"
   ::= { vmwVRNIEvents 70011}

vmwEdgeVMNotRespondingEvent NOTIFICATION-TYPE
   OBJECTS { vmwEventSeverity, vmwAffectedObject, vmwOperatorDesc, vmwVrniUrl, vmwTimestamp, vmwEventName }
   STATUS current
   DESCRIPTION
      "Edge VM Responding Event"
   ::= { vmwVRNIEvents 70012}

vmwEdgeUnhealthyEvent NOTIFICATION-TYPE
   OBJECTS { vmwEventSeverity, vmwAffectedObject, vmwOperatorDesc, vmwVrniUrl, vmwTimestamp, vmwEventName }
   STATUS current
   DESCRIPTION
      "Edge Health Event"
   ::= { vmwVRNIEvents 70013}

vmwEdgeVMCommunicationFailureEvent NOTIFICATION-TYPE
   OBJECTS { vmwEventSeverity, vmwAffectedObject, vmwOperatorDesc, vmwVrniUrl, vmwTimestamp, vmwEventName }
   STATUS current
   DESCRIPTION
      "Edge communication failure Event"
   ::= { vmwVRNIEvents 70014}

vmwNSXEdgeEvent NOTIFICATION-TYPE
   OBJECTS { vmwEventSeverity, vmwAffectedObject, vmwOperatorDesc, vmwVrniUrl, vmwTimestamp, vmwEventName }
   STATUS current
   DESCRIPTION
      "NSX Edge Event"
   ::= { vmwVRNIEvents 70015}

vmwPanEvent NOTIFICATION-TYPE
   OBJECTS { vmwEventSeverity, vmwAffectedObject, vmwOperatorDesc, vmwVrniUrl, vmwTimestamp, vmwEventName }
   STATUS current
   DESCRIPTION
      "Palo Alto Event"
   ::= { vmwVRNIEvents 80000}

vmwPanNsxNotInRegisteredStateEvent NOTIFICATION-TYPE
   OBJECTS { vmwEventSeverity, vmwAffectedObject, vmwOperatorDesc, vmwVrniUrl, vmwTimestamp, vmwEventName }
   STATUS current
   DESCRIPTION
      "Palo Alto NSX Registration Event"
   ::= { vmwVRNIEvents 80001}

vmwPanNsxDynamicUpdateDelayedEvent NOTIFICATION-TYPE
   OBJECTS { vmwEventSeverity, vmwAffectedObject, vmwOperatorDesc, vmwVrniUrl, vmwTimestamp, vmwEventName }
   STATUS current
   DESCRIPTION
      "Palo Alto NSX Dynamic Update Event"
   ::= { vmwVRNIEvents 80002}

vmwPanDeviceInDisconnectedStateEvent NOTIFICATION-TYPE
   OBJECTS { vmwEventSeverity, vmwAffectedObject, vmwOperatorDesc, vmwVrniUrl, vmwTimestamp, vmwEventName }
   STATUS current
   DESCRIPTION
      "Palo Alto Device Disconnect Event"
   ::= { vmwVRNIEvents 80003}

vmwPanNsxServiceApplianceViewMismatchEvent NOTIFICATION-TYPE
   OBJECTS { vmwEventSeverity, vmwAffectedObject, vmwOperatorDesc, vmwVrniUrl, vmwTimestamp, vmwEventName }
   STATUS current
   DESCRIPTION
      "Palo Alto Service Device Mismatch Event"
   ::= { vmwVRNIEvents 80004}

vmwPanNsxFabricAgentNotFoundOnHostEvent NOTIFICATION-TYPE
   OBJECTS { vmwEventSeverity, vmwAffectedObject, vmwOperatorDesc, vmwVrniUrl, vmwTimestamp, vmwEventName }
   STATUS current
   DESCRIPTION
      "NSX Fabric Agent Not Found Event"
   ::= { vmwVRNIEvents 80005}

vmwPanNsxServiceVMNotFoundOnHostEvent NOTIFICATION-TYPE
   OBJECTS { vmwEventSeverity, vmwAffectedObject, vmwOperatorDesc, vmwVrniUrl, vmwTimestamp, vmwEventName }
   STATUS current
   DESCRIPTION
      "Palo Alto Service VM Not Found Event"
   ::= { vmwVRNIEvents 80006}

vmwCheckpointEvent NOTIFICATION-TYPE
   OBJECTS { vmwEventSeverity, vmwAffectedObject, vmwOperatorDesc, vmwVrniUrl, vmwTimestamp, vmwEventName }
   STATUS current
   DESCRIPTION
      "Check Point Event"
   ::= { vmwVRNIEvents 80100}

vmwCheckpointNsxFabricAgentNotFoundOnHostEvent NOTIFICATION-TYPE
   OBJECTS { vmwEventSeverity, vmwAffectedObject, vmwOperatorDesc, vmwVrniUrl, vmwTimestamp, vmwEventName }
   STATUS current
   DESCRIPTION
      "Check Point NSX Fabric Agent Not Found Event"
   ::= { vmwVRNIEvents 80102}

vmwCheckpointNsxServiceVMNotFoundOnHostEvent NOTIFICATION-TYPE
   OBJECTS { vmwEventSeverity, vmwAffectedObject, vmwOperatorDesc, vmwVrniUrl, vmwTimestamp, vmwEventName }
   STATUS current
   DESCRIPTION
      "Check Point Service VM Not Found Event"
   ::= { vmwVRNIEvents 80103}

vmwCheckpointGatewaySicStatusNotCommunicatingEvent NOTIFICATION-TYPE
   OBJECTS { vmwEventSeverity, vmwAffectedObject, vmwOperatorDesc, vmwVrniUrl, vmwTimestamp, vmwEventName }
   STATUS current
   DESCRIPTION
      "Check Point Gateway Sic Status Not Communicating Event"
   ::= { vmwVRNIEvents 80104}

vmwCheckpointNsxServiceApplianceViewMismatchEvent NOTIFICATION-TYPE
   OBJECTS { vmwEventSeverity, vmwAffectedObject, vmwOperatorDesc, vmwVrniUrl, vmwTimestamp, vmwEventName }
   STATUS current
   DESCRIPTION
      "Check Point Service VM Mismatch Event"
   ::= { vmwVRNIEvents 80105}

vmwCriticalHostNotAccessibleEvent NOTIFICATION-TYPE
   OBJECTS { vmwEventSeverity, vmwAffectedObject, vmwOperatorDesc, vmwVrniUrl, vmwTimestamp, vmwEventName }
   STATUS current
   DESCRIPTION
      "Host with VMs running critical services is not accessible"
   ::= { vmwVRNIEvents 40001}

vmwIndexerLagEvent NOTIFICATION-TYPE
   OBJECTS { vmwEventSeverity, vmwAffectedObject, vmwOperatorDesc, vmwVrniUrl, vmwTimestamp, vmwEventName }
   STATUS current
   DESCRIPTION
      "Index Lag Event"
   ::= { vmwVRNIEvents 80501}

vmwIPFIXFlowDPPausedEvent NOTIFICATION-TYPE
   OBJECTS { vmwEventSeverity, vmwAffectedObject, vmwOperatorDesc, vmwVrniUrl, vmwTimestamp, vmwEventName }
   STATUS current
   DESCRIPTION
      "IPFIX Flow Data Provider Paused Event"
   ::= { vmwVRNIEvents 80502}

vmwGridProcessingStoppedEvent NOTIFICATION-TYPE
   OBJECTS { vmwEventSeverity, vmwAffectedObject, vmwOperatorDesc, vmwVrniUrl, vmwTimestamp, vmwEventName }
   STATUS current
   DESCRIPTION
      "Grid Processing Stopped Event"
   ::= { vmwVRNIEvents 80503}

vmwUnableToSendEmailsEvent NOTIFICATION-TYPE
   OBJECTS { vmwEventSeverity, vmwAffectedObject, vmwOperatorDesc, vmwVrniUrl, vmwTimestamp, vmwEventName }
   STATUS current
   DESCRIPTION
      "Unable to Send Emails Event"
   ::= { vmwVRNIEvents 80504}

vmwSMTPNotConfiguredEvent NOTIFICATION-TYPE
   OBJECTS { vmwEventSeverity, vmwAffectedObject, vmwOperatorDesc, vmwVrniUrl, vmwTimestamp, vmwEventName }
   STATUS current
   DESCRIPTION
      "SMPT Not Configured Event"
   ::= { vmwVRNIEvents 80505}

vmwSNMPNotConfiguredEvent NOTIFICATION-TYPE
   OBJECTS { vmwEventSeverity, vmwAffectedObject, vmwOperatorDesc, vmwVrniUrl, vmwTimestamp, vmwEventName }
   STATUS current
   DESCRIPTION
      "SNMP Not Configured Event"
   ::= { vmwVRNIEvents 80506}

vmwReindexingInProgressEvent NOTIFICATION-TYPE
   OBJECTS { vmwEventSeverity, vmwAffectedObject, vmwOperatorDesc, vmwVrniUrl, vmwTimestamp, vmwEventName }
   STATUS current
   DESCRIPTION
      "Redindexing In Process Event"
   ::= { vmwVRNIEvents 80507}

vmwNodesVersionMismatchEvent NOTIFICATION-TYPE
   OBJECTS { vmwEventSeverity, vmwAffectedObject, vmwOperatorDesc, vmwVrniUrl, vmwTimestamp, vmwEventName }
   STATUS current
   DESCRIPTION
      "Node Version Mismatch Event"
   ::= { vmwVRNIEvents 80508}

vmwNotAllServicesRunningEvent NOTIFICATION-TYPE
   OBJECTS { vmwEventSeverity, vmwAffectedObject, vmwOperatorDesc, vmwVrniUrl, vmwTimestamp, vmwEventName }
   STATUS current
   DESCRIPTION
      "Not All Services Running Event"
   ::= { vmwVRNIEvents 80509}

vmwNotAllServicesHealthyEvent NOTIFICATION-TYPE
   OBJECTS { vmwEventSeverity, vmwAffectedObject, vmwOperatorDesc, vmwVrniUrl, vmwTimestamp, vmwEventName }
   STATUS current
   DESCRIPTION
      "Not All Services Healthy Event"
   ::= { vmwVRNIEvents 80510}

vmwExpandPartitionFailedEvent NOTIFICATION-TYPE
   OBJECTS { vmwEventSeverity, vmwAffectedObject, vmwOperatorDesc, vmwVrniUrl, vmwTimestamp, vmwEventName }
   STATUS current
   DESCRIPTION
      "Expand Partition Failed Event"
   ::= { vmwVRNIEvents 80511}

vmwDiskCleanupFailedEvent NOTIFICATION-TYPE
   OBJECTS { vmwEventSeverity, vmwAffectedObject, vmwOperatorDesc, vmwVrniUrl, vmwTimestamp, vmwEventName }
   STATUS current
   DESCRIPTION
      "Disk Cleanup Failed Event"
   ::= { vmwVRNIEvents 80512}

vmwVaccumFailedEvent NOTIFICATION-TYPE
   OBJECTS { vmwEventSeverity, vmwAffectedObject, vmwOperatorDesc, vmwVrniUrl, vmwTimestamp, vmwEventName }
   STATUS current
   DESCRIPTION
      "Vacuum Failed Event"
   ::= { vmwVRNIEvents 80513}

vmwConfigStoreCleanupFailedEvent NOTIFICATION-TYPE
   OBJECTS { vmwEventSeverity, vmwAffectedObject, vmwOperatorDesc, vmwVrniUrl, vmwTimestamp, vmwEventName }
   STATUS current
   DESCRIPTION
      "Config Store Cleanup Failed Event"
   ::= { vmwVRNIEvents 80514}

vmwHBaseRetentionToolFailedEvent NOTIFICATION-TYPE
   OBJECTS { vmwEventSeverity, vmwAffectedObject, vmwOperatorDesc, vmwVrniUrl, vmwTimestamp, vmwEventName }
   STATUS current
   DESCRIPTION
      "HBASE Retention Tool Failed Event"
   ::= { vmwVRNIEvents 80515}

vmwMetricStoreUpdaterFailedEvent NOTIFICATION-TYPE
   OBJECTS { vmwEventSeverity, vmwAffectedObject, vmwOperatorDesc, vmwVrniUrl, vmwTimestamp, vmwEventName }
   STATUS current
   DESCRIPTION
      "Metric Store Updater Failed Event"
   ::= { vmwVRNIEvents 80516}

vmwCollectorLagEvent NOTIFICATION-TYPE
   OBJECTS { vmwEventSeverity, vmwAffectedObject, vmwOperatorDesc, vmwVrniUrl, vmwTimestamp, vmwEventName }
   STATUS current
   DESCRIPTION
      "Collecter Lag Event"
   ::= { vmwVRNIEvents 80517}

vmwCollectionLagEvent NOTIFICATION-TYPE
   OBJECTS { vmwEventSeverity, vmwAffectedObject, vmwOperatorDesc, vmwVrniUrl, vmwTimestamp, vmwEventName }
   STATUS current
   DESCRIPTION
      "Collection Lag Event"
   ::= { vmwVRNIEvents 80518}

vmwGridProcessingLagEvent NOTIFICATION-TYPE
   OBJECTS { vmwEventSeverity, vmwAffectedObject, vmwOperatorDesc, vmwVrniUrl, vmwTimestamp, vmwEventName }
   STATUS current
   DESCRIPTION
      "Grid Processing Lag Event"
   ::= { vmwVRNIEvents 80519}

vmwConnectionErrorEvent NOTIFICATION-TYPE
   OBJECTS { vmwEventSeverity, vmwAffectedObject, vmwOperatorDesc, vmwVrniUrl, vmwTimestamp, vmwEventName }
   STATUS current
   DESCRIPTION
      "Connection Error Event"
   ::= { vmwVRNIEvents 80520}

vmwNodeNotActiveEvent NOTIFICATION-TYPE
   OBJECTS { vmwEventSeverity, vmwAffectedObject, vmwOperatorDesc, vmwVrniUrl, vmwTimestamp, vmwEventName }
   STATUS current
   DESCRIPTION
      "Node Not Active Event"
   ::= { vmwVRNIEvents 80521}

vmwHighDiskUtilizationEvent NOTIFICATION-TYPE
   OBJECTS { vmwEventSeverity, vmwAffectedObject, vmwOperatorDesc, vmwVrniUrl, vmwTimestamp, vmwEventName }
   STATUS current
   DESCRIPTION
      "High Disk Utilization Event"
   ::= { vmwVRNIEvents 80522}

vmwIndexingAbortedEvent NOTIFICATION-TYPE
   OBJECTS { vmwEventSeverity, vmwAffectedObject, vmwOperatorDesc, vmwVrniUrl, vmwTimestamp, vmwEventName }
   STATUS current
   DESCRIPTION
      "Indexing Aborted Event"
   ::= { vmwVRNIEvents 80523}

vmwUpgradeFailedEvent NOTIFICATION-TYPE
   OBJECTS { vmwEventSeverity, vmwAffectedObject, vmwOperatorDesc, vmwVrniUrl, vmwTimestamp, vmwEventName }
   STATUS current
   DESCRIPTION
      "Upgrade Failed Event"
   ::= { vmwVRNIEvents 80524}

vmwFlowProcessingSuspendedEvent NOTIFICATION-TYPE
   OBJECTS { vmwEventSeverity, vmwAffectedObject, vmwOperatorDesc, vmwVrniUrl, vmwTimestamp, vmwEventName }
   STATUS current
   DESCRIPTION
      "Flow Processing Suspended Event"
   ::= { vmwVRNIEvents 80525}

vmwVCNotOnSameProxyEvent NOTIFICATION-TYPE
   OBJECTS { vmwEventSeverity, vmwAffectedObject, vmwOperatorDesc, vmwVrniUrl, vmwTimestamp, vmwEventName }
   STATUS current
   DESCRIPTION
      "VC_NOT_ON_SAME_PROXY_EVENT"
   ::= { vmwVRNIEvents 80643}

vmwNoDVSAvailableEvent NOTIFICATION-TYPE
   OBJECTS { vmwEventSeverity, vmwAffectedObject, vmwOperatorDesc, vmwVrniUrl, vmwTimestamp, vmwEventName }
   STATUS current
   DESCRIPTION
      "NO_DVS_AVAILABLE_EVENT"
   ::= { vmwVRNIEvents 80642}

vmwUnknownInfobloxVersionEvent NOTIFICATION-TYPE
   OBJECTS { vmwEventSeverity, vmwAffectedObject, vmwOperatorDesc, vmwVrniUrl, vmwTimestamp, vmwEventName }
   STATUS current
   DESCRIPTION
      "Infoblox version cannot be determined"
   ::= { vmwVRNIEvents 80641}

vmwUnsupportedInfobloxVersionEvent NOTIFICATION-TYPE
   OBJECTS { vmwEventSeverity, vmwAffectedObject, vmwOperatorDesc, vmwVrniUrl, vmwTimestamp, vmwEventName }
   STATUS current
   DESCRIPTION
      "The version of Infoblox is not supported"
   ::= { vmwVRNIEvents 80640}

vmwIncorrectInfobloxCredentialEvent NOTIFICATION-TYPE
   OBJECTS { vmwEventSeverity, vmwAffectedObject, vmwOperatorDesc, vmwVrniUrl, vmwTimestamp, vmwEventName }
   STATUS current
   DESCRIPTION
      "Invalid credentials or insufficient privileges"
   ::= { vmwVRNIEvents 80639}

vmwInfobloxRecordLimitExceededEvent NOTIFICATION-TYPE
   OBJECTS { vmwEventSeverity, vmwAffectedObject, vmwOperatorDesc, vmwVrniUrl, vmwTimestamp, vmwEventName }
   STATUS current
   DESCRIPTION
      "The number of A records fetched from Infoblox exceeds the current limit"
   ::= { vmwVRNIEvents 80638}

vmwWebhookNotRunningEvent NOTIFICATION-TYPE
   OBJECTS { vmwEventSeverity, vmwAffectedObject, vmwOperatorDesc, vmwVrniUrl, vmwTimestamp, vmwEventName }
   STATUS current
   DESCRIPTION
      "WEBHOOK_NOT_RUNNING_EVENT"
   ::= { vmwVRNIEvents 80637}

vmwIncorrectWebhookConfiguredOnAlertEvent NOTIFICATION-TYPE
   OBJECTS { vmwEventSeverity, vmwAffectedObject, vmwOperatorDesc, vmwVrniUrl, vmwTimestamp, vmwEventName }
   STATUS current
   DESCRIPTION
      "INCORRECT_WEBHOOK_CONFIGURED_ON_ALERT_EVENT"
   ::= { vmwVRNIEvents 80636}

vmwWebhookNotEnabledOnAlertEvent NOTIFICATION-TYPE
   OBJECTS { vmwEventSeverity, vmwAffectedObject, vmwOperatorDesc, vmwVrniUrl, vmwTimestamp, vmwEventName }
   STATUS current
   DESCRIPTION
      "WEBHOOK_NOT_ENABLED_ON_ALERT_EVENT"
   ::= { vmwVRNIEvents 80635}

vmwVRNIContentPackNotInstalledEvent NOTIFICATION-TYPE
   OBJECTS { vmwEventSeverity, vmwAffectedObject, vmwOperatorDesc, vmwVrniUrl, vmwTimestamp, vmwEventName }
   STATUS current
   DESCRIPTION
      "vRNI_CONTENT_PACK_NOT_INSTALLED_EVENT"
   ::= { vmwVRNIEvents 80634}

vmwUnsupportedVRNIContentPackVersionEvent NOTIFICATION-TYPE
   OBJECTS { vmwEventSeverity, vmwAffectedObject, vmwOperatorDesc, vmwVrniUrl, vmwTimestamp, vmwEventName }
   STATUS current
   DESCRIPTION
      "UNSUPPORTED_vRNI_CONTENT_PACK_VERSION_EVENT"
   ::= { vmwVRNIEvents 80633}

vmwUnsupportedLogInsightVersionEvent NOTIFICATION-TYPE
   OBJECTS { vmwEventSeverity, vmwAffectedObject, vmwOperatorDesc, vmwVrniUrl, vmwTimestamp, vmwEventName }
   STATUS current
   DESCRIPTION
      "UNSUPPORTED_LOG_INSIGHT_VERSION_EVENT"
   ::= { vmwVRNIEvents 80632}

vmwComputeManagersNotAddedEvent NOTIFICATION-TYPE
   OBJECTS { vmwEventSeverity, vmwAffectedObject, vmwOperatorDesc, vmwVrniUrl, vmwTimestamp, vmwEventName }
   STATUS current
   DESCRIPTION
      "COMPUTE_MANAGERS_NOT_ADDED_EVENT"
   ::= { vmwVRNIEvents 80631}

vmwComputeManagersNotFoundEvent NOTIFICATION-TYPE
   OBJECTS { vmwEventSeverity, vmwAffectedObject, vmwOperatorDesc, vmwVrniUrl, vmwTimestamp, vmwEventName }
   STATUS current
   DESCRIPTION
      "COMPUTE_MANAGERS_NOT_FOUND_EVENT"
   ::= { vmwVRNIEvents 80630}

vmwUnsupportedNSXTVersionEvent NOTIFICATION-TYPE
   OBJECTS { vmwEventSeverity, vmwAffectedObject, vmwOperatorDesc, vmwVrniUrl, vmwTimestamp, vmwEventName }
   STATUS current
   DESCRIPTION
      "UNSUPPORTED_NSXT_VERSION_EVENT"
   ::= { vmwVRNIEvents 80629}

vmwNotEmptyNodeEvent NOTIFICATION-TYPE
   OBJECTS { vmwEventSeverity, vmwAffectedObject, vmwOperatorDesc, vmwVrniUrl, vmwTimestamp, vmwEventName }
   STATUS current
   DESCRIPTION
      "NOT_EMPTY_NODE_EVENT"
   ::= { vmwVRNIEvents 80628}

vmwFlowPhysicalNodeEvent NOTIFICATION-TYPE
   OBJECTS { vmwEventSeverity, vmwAffectedObject, vmwOperatorDesc, vmwVrniUrl, vmwTimestamp, vmwEventName }
   STATUS current
   DESCRIPTION
      "FLOW_PHYSICAL_NODE_EVENT"
   ::= { vmwVRNIEvents 80627}

vmwFlowCollectionErrorEvent NOTIFICATION-TYPE
   OBJECTS { vmwEventSeverity, vmwAffectedObject, vmwOperatorDesc, vmwVrniUrl, vmwTimestamp, vmwEventName }
   STATUS current
   DESCRIPTION
      "FLOW_COLLECTION_ERROR_EVENT"
   ::= { vmwVRNIEvents 8061313}

vmwAWSThrottlingExceptionEvent NOTIFICATION-TYPE
   OBJECTS { vmwEventSeverity, vmwAffectedObject, vmwOperatorDesc, vmwVrniUrl, vmwTimestamp, vmwEventName }
   STATUS current
   DESCRIPTION
      "AWS_THROTTLING_EXCEPTION_EVENT"
   ::= { vmwVRNIEvents 8061314}

vmwAWSFlowLogAccessDeniedExceptionEvent NOTIFICATION-TYPE
   OBJECTS { vmwEventSeverity, vmwAffectedObject, vmwOperatorDesc, vmwVrniUrl, vmwTimestamp, vmwEventName }
   STATUS current
   DESCRIPTION
      "AWS_FLOW_LOG_ACCESS_DENIED_EXCEPTION_EVENT"
   ::= { vmwVRNIEvents 8061315}

vmwNSXIPFIXStatusMismatchEvent NOTIFICATION-TYPE
   OBJECTS { vmwEventSeverity, vmwAffectedObject, vmwOperatorDesc, vmwVrniUrl, vmwTimestamp, vmwEventName }
   STATUS current
   DESCRIPTION
      "NSX_IPFIX_STATUS_MISMATCH_EVENT"
   ::= { vmwVRNIEvents 80626}

vmwNumVMsOrHostsNotFoundEvent NOTIFICATION-TYPE
   OBJECTS { vmwEventSeverity, vmwAffectedObject, vmwOperatorDesc, vmwVrniUrl, vmwTimestamp, vmwEventName }
   STATUS current
   DESCRIPTION
      "NUM_VMS_OR_HOSTS_NOT_FOUND_EVENT"
   ::= { vmwVRNIEvents 80625}

vmwUnsupportedNSXVersionEvent NOTIFICATION-TYPE
   OBJECTS { vmwEventSeverity, vmwAffectedObject, vmwOperatorDesc, vmwVrniUrl, vmwTimestamp, vmwEventName }
   STATUS current
   DESCRIPTION
      "UNSUPPORTED_NSX_VERSION_EVENT"
   ::= { vmwVRNIEvents 806100018}

vmwPwdAuthModeDisabledAristaEvent NOTIFICATION-TYPE
   OBJECTS { vmwEventSeverity, vmwAffectedObject, vmwOperatorDesc, vmwVrniUrl, vmwTimestamp, vmwEventName }
   STATUS current
   DESCRIPTION
      "PWD_AUTH_MODE_DISABLED_ARISTA_EVENT"
   ::= { vmwVRNIEvents 806100012}

vmwHostnameResolutionErrorEvent NOTIFICATION-TYPE
   OBJECTS { vmwEventSeverity, vmwAffectedObject, vmwOperatorDesc, vmwVrniUrl, vmwTimestamp, vmwEventName }
   STATUS current
   DESCRIPTION
      "HOSTNAME_RESOLUTION_ERROR_EVENT"
   ::= { vmwVRNIEvents 80624}

vmwPrimaryNSXNotAddedEvent NOTIFICATION-TYPE
   OBJECTS { vmwEventSeverity, vmwAffectedObject, vmwOperatorDesc, vmwVrniUrl, vmwTimestamp, vmwEventName }
   STATUS current
   DESCRIPTION
      "PRIMARY_NSX_NOT_ADDED_EVENT"
   ::= { vmwVRNIEvents 80623}

vmwDataProviderNotRunningEvent NOTIFICATION-TYPE
   OBJECTS { vmwEventSeverity, vmwAffectedObject, vmwOperatorDesc, vmwVrniUrl, vmwTimestamp, vmwEventName }
   STATUS current
   DESCRIPTION
      "DATA_PROVIDER_NOT_RUNNING_EVENT"
   ::= { vmwVRNIEvents 80622}

vmwInvalidResponseFromDatasourceEvent NOTIFICATION-TYPE
   OBJECTS { vmwEventSeverity, vmwAffectedObject, vmwOperatorDesc, vmwVrniUrl, vmwTimestamp, vmwEventName }
   STATUS current
   DESCRIPTION
      "INVALID_RESPONSE_FROM_DATASOURCE_EVENT"
   ::= { vmwVRNIEvents 80621}

vmwHostNotReachableEvent NOTIFICATION-TYPE
   OBJECTS { vmwEventSeverity, vmwAffectedObject, vmwOperatorDesc, vmwVrniUrl, vmwTimestamp, vmwEventName }
   STATUS current
   DESCRIPTION
      "HOST_NOT_REACHABLE_EVENT"
   ::= { vmwVRNIEvents 80620}

vmwNSXControllerNotFoundEvent NOTIFICATION-TYPE
   OBJECTS { vmwEventSeverity, vmwAffectedObject, vmwOperatorDesc, vmwVrniUrl, vmwTimestamp, vmwEventName }
   STATUS current
   DESCRIPTION
      "NSX_CONTROLLER_NOT_FOUND_EVENT"
   ::= { vmwVRNIEvents 80619}

vmwUnexpectedDSTypeOrVersionEvent NOTIFICATION-TYPE
   OBJECTS { vmwEventSeverity, vmwAffectedObject, vmwOperatorDesc, vmwVrniUrl, vmwTimestamp, vmwEventName }
   STATUS current
   DESCRIPTION
      "UNEXPECTED_DS_TYPE_OR_VERSION_EVENT"
   ::= { vmwVRNIEvents 80618}

vmwWarnConfigEvent NOTIFICATION-TYPE
   OBJECTS { vmwEventSeverity, vmwAffectedObject, vmwOperatorDesc, vmwVrniUrl, vmwTimestamp, vmwEventName }
   STATUS current
   DESCRIPTION
      "WARN_CONFIG_EVENT"
   ::= { vmwVRNIEvents 80617}

vmwInvalidConfigEvent NOTIFICATION-TYPE
   OBJECTS { vmwEventSeverity, vmwAffectedObject, vmwOperatorDesc, vmwVrniUrl, vmwTimestamp, vmwEventName }
   STATUS current
   DESCRIPTION
      "INVALID_CONFIG_EVENT"
   ::= { vmwVRNIEvents 80616}

vmwNotFoundEvent NOTIFICATION-TYPE
   OBJECTS { vmwEventSeverity, vmwAffectedObject, vmwOperatorDesc, vmwVrniUrl, vmwTimestamp, vmwEventName }
   STATUS current
   DESCRIPTION
      "NOT_FOUND_EVENT"
   ::= { vmwVRNIEvents 80614}

vmwInsufficientPrivilegesEvent NOTIFICATION-TYPE
   OBJECTS { vmwEventSeverity, vmwAffectedObject, vmwOperatorDesc, vmwVrniUrl, vmwTimestamp, vmwEventName }
   STATUS current
   DESCRIPTION
      "INSUFFICIENT_PRIVILEGES_EVENT"
   ::= { vmwVRNIEvents 80613}

vmwPwdAuthModeDisabledEvent NOTIFICATION-TYPE
   OBJECTS { vmwEventSeverity, vmwAffectedObject, vmwOperatorDesc, vmwVrniUrl, vmwTimestamp, vmwEventName }
   STATUS current
   DESCRIPTION
      "PWD_AUTH_MODE_DISABLED_EVENT"
   ::= { vmwVRNIEvents 80612}

vmwFailedCredsEncryptEvent NOTIFICATION-TYPE
   OBJECTS { vmwEventSeverity, vmwAffectedObject, vmwOperatorDesc, vmwVrniUrl, vmwTimestamp, vmwEventName }
   STATUS current
   DESCRIPTION
      "FAILED_CREDS_ENCRYPT_EVENT"
   ::= { vmwVRNIEvents 80611}

vmwSNMPConnectionInvalidEvent NOTIFICATION-TYPE
   OBJECTS { vmwEventSeverity, vmwAffectedObject, vmwOperatorDesc, vmwVrniUrl, vmwTimestamp, vmwEventName }
   STATUS current
   DESCRIPTION
      "SNMP_CONNECTION_INVALID_EVENT"
   ::= { vmwVRNIEvents 80609}

vmwUnknownHostEvent NOTIFICATION-TYPE
   OBJECTS { vmwEventSeverity, vmwAffectedObject, vmwOperatorDesc, vmwVrniUrl, vmwTimestamp, vmwEventName }
   STATUS current
   DESCRIPTION
      "UNKNOWN_HOST_EVENT"
   ::= { vmwVRNIEvents 80608}

vmwInvalidCredentialsEvent NOTIFICATION-TYPE
   OBJECTS { vmwEventSeverity, vmwAffectedObject, vmwOperatorDesc, vmwVrniUrl, vmwTimestamp, vmwEventName }
   STATUS current
   DESCRIPTION
      "INVALID_CREDENTIALS_EVENT"
   ::= { vmwVRNIEvents 80606}

vmwIncorrectConnectionStringEvent NOTIFICATION-TYPE
   OBJECTS { vmwEventSeverity, vmwAffectedObject, vmwOperatorDesc, vmwVrniUrl, vmwTimestamp, vmwEventName }
   STATUS current
   DESCRIPTION
      "INCORRECT_CONNECTION_STRING_EVENT"
   ::= { vmwVRNIEvents 80605}

vmwConnectionRefusedEvent NOTIFICATION-TYPE
   OBJECTS { vmwEventSeverity, vmwAffectedObject, vmwOperatorDesc, vmwVrniUrl, vmwTimestamp, vmwEventName }
   STATUS current
   DESCRIPTION
      "CONNECTION_REFUSED_EVENT"
   ::= { vmwVRNIEvents 80603}

vmwTimeoutEvent NOTIFICATION-TYPE
   OBJECTS { vmwEventSeverity, vmwAffectedObject, vmwOperatorDesc, vmwVrniUrl, vmwTimestamp, vmwEventName }
   STATUS current
   DESCRIPTION
      "TIMEOUT_EVENT"
   ::= { vmwVRNIEvents 80602}

vmwFailedEvent NOTIFICATION-TYPE
   OBJECTS { vmwEventSeverity, vmwAffectedObject, vmwOperatorDesc, vmwVrniUrl, vmwTimestamp, vmwEventName }
   STATUS current
   DESCRIPTION
      "FAILED_EVENT"
   ::= { vmwVRNIEvents 80601}

vmwNSXTEvent NOTIFICATION-TYPE
   OBJECTS { vmwEventSeverity, vmwAffectedObject, vmwOperatorDesc, vmwVrniUrl, vmwTimestamp, vmwEventName }
   STATUS current
   DESCRIPTION
      "NSX-T Event"
   ::= { vmwVRNIEvents 80200}

vmwNSXTVcNotAddedEvent NOTIFICATION-TYPE
   OBJECTS { vmwEventSeverity, vmwAffectedObject, vmwOperatorDesc, vmwVrniUrl, vmwTimestamp, vmwEventName }
   STATUS current
   DESCRIPTION
      "VC Not Added As Data Source Event"
   ::= { vmwVRNIEvents 80201}

vmwNSXTStandaloneHostsEvent NOTIFICATION-TYPE
   OBJECTS { vmwEventSeverity, vmwAffectedObject, vmwOperatorDesc, vmwVrniUrl, vmwTimestamp, vmwEventName }
   STATUS current
   DESCRIPTION
      "Standalone hosts added in NSX-T Event"
   ::= { vmwVRNIEvents 80202}

vmwLargeSdmsDroppedEvent NOTIFICATION-TYPE
   OBJECTS { vmwEventSeverity, vmwAffectedObject, vmwOperatorDesc, vmwVrniUrl, vmwTimestamp, vmwEventName }
   STATUS current
   DESCRIPTION
      "Data Processing Error"
   ::= { vmwVRNIEvents 80526}

vmwNSXTIPFixDFWStatusNotEnabledEvent NOTIFICATION-TYPE
   OBJECTS { vmwEventSeverity, vmwAffectedObject, vmwOperatorDesc, vmwVrniUrl, vmwTimestamp, vmwEventName }
   STATUS current
   DESCRIPTION
      "NSXT_IPFIX_DFW_STATUS_NOT_ENABLED_EVENT"
   ::= { vmwVRNIEvents 80650}

vmwNSXTIPFixPortIncorrectEvent NOTIFICATION-TYPE
   OBJECTS { vmwEventSeverity, vmwAffectedObject, vmwOperatorDesc, vmwVrniUrl, vmwTimestamp, vmwEventName }
   STATUS current
   DESCRIPTION
      "NSXT_IPFIX_PORT_INCORRECT_EVENT"
   ::= { vmwVRNIEvents 80649}

vmwNSXTIPFixCollectorAndIPFixProfileMismatchEvent NOTIFICATION-TYPE
   OBJECTS { vmwEventSeverity, vmwAffectedObject, vmwOperatorDesc, vmwVrniUrl, vmwTimestamp, vmwEventName }
   STATUS current
   DESCRIPTION
      "NSXT_IPFIX_COLLECTOR_AND_IPFIX_PROFILE_MISMATCH_EVENT"
   ::= { vmwVRNIEvents 80648}

vmwNSXTIPFixIPFixProfilePriorityNotZeroEvent NOTIFICATION-TYPE
   OBJECTS { vmwEventSeverity, vmwAffectedObject, vmwOperatorDesc, vmwVrniUrl, vmwTimestamp, vmwEventName }
   STATUS current
   DESCRIPTION
      "NSXT_IPFIX_IPFIX_PROFILE_PRIORITY_NOT_ZERO_EVENT"
   ::= { vmwVRNIEvents 80647}

vmwNSXTIPFixNoIPFixProfileEvent NOTIFICATION-TYPE
   OBJECTS { vmwEventSeverity, vmwAffectedObject, vmwOperatorDesc, vmwVrniUrl, vmwTimestamp, vmwEventName }
   STATUS current
   DESCRIPTION
      "NSXT_IPFIX_NO_IPFIX_PROFILE_EVENT"
   ::= { vmwVRNIEvents 80646}

vmwNSXTIPFixNoNewCollectorProfileCanBeAddedEvent NOTIFICATION-TYPE
   OBJECTS { vmwEventSeverity, vmwAffectedObject, vmwOperatorDesc, vmwVrniUrl, vmwTimestamp, vmwEventName }
   STATUS current
   DESCRIPTION
      "NSXT_IPFIX_NO_NEW_COLLECTOR_PROFILE_CAN_BE_ADDED_EVENT"
   ::= { vmwVRNIEvents 80645}

vmwNSXTIPFixNoCollectorProfileEvent NOTIFICATION-TYPE
   OBJECTS { vmwEventSeverity, vmwAffectedObject, vmwOperatorDesc, vmwVrniUrl, vmwTimestamp, vmwEventName }
   STATUS current
   DESCRIPTION
      "NSXT_IPFIX_NO_COLLECTOR_PROFILE_EVENT"
   ::= { vmwVRNIEvents 80644}

vmwNSXTSystemEvent NOTIFICATION-TYPE
   OBJECTS { vmwEventSeverity, vmwAffectedObject, vmwOperatorDesc, vmwVrniUrl, vmwTimestamp, vmwEventName }
   STATUS current
   DESCRIPTION
      "These are the alarms/events reported by NSX-T. 'Source Component' specifies the entity emmitting this event.
      It can be Manager/Controller/Edge. Combination of fields like Source Component, Event Type, Severity and message can be used to troubleshoot NSX-T appliance.
      For further information, log into NSX-T Manager UI and visit Dashboard"
   ::= { vmwVRNIEvents 80203}

vmwNSXTNoUplinkConnectivityEvent NOTIFICATION-TYPE
   OBJECTS { vmwEventSeverity, vmwAffectedObject, vmwOperatorDesc, vmwVrniUrl, vmwTimestamp, vmwEventName }
   STATUS current
   DESCRIPTION
      "NSX-T Tier-1 logical router is disconnected from Tier-0 router. Networks under this router are not reachable from outside and vice versa.
      For more details, please log into vRNI, navigate to Settings -> Events"
   ::= { vmwVRNIEvents 80205}

vmwNSXTRoutingAdvertisementEvent NOTIFICATION-TYPE
   OBJECTS { vmwEventSeverity, vmwAffectedObject, vmwOperatorDesc, vmwVrniUrl, vmwTimestamp, vmwEventName }
   STATUS current
   DESCRIPTION
      "Routing advertisement is disabled for NSX-T Tier-1 logical router. Networks under this router are not reachable from outside.
      For more details, please log into vRNI, navigate to Settings -> Events"
   ::= { vmwVRNIEvents 80206}

vmwNSXTManagerConnectivityDownEvent NOTIFICATION-TYPE
   OBJECTS { vmwEventSeverity, vmwAffectedObject, vmwOperatorDesc, vmwVrniUrl, vmwTimestamp, vmwEventName }
   STATUS current
   DESCRIPTION
      "NSX-T Edge Node has lost manager connectivity.
       For more details, please log into vRNI, navigate to Settings -> Events"
   ::= { vmwVRNIEvents 80207}

vmwNSXTControllerConnectivityDegradedEvent NOTIFICATION-TYPE
   OBJECTS { vmwEventSeverity, vmwAffectedObject, vmwOperatorDesc, vmwVrniUrl, vmwTimestamp, vmwEventName }
   STATUS current
   DESCRIPTION
      "NSX-T Edge Node is not able to communicate with one or more controllers.
      For more details, please log into vRNI, navigate to Settings -> Events"
   ::= { vmwVRNIEvents 80208}

vmwNSXTControllerConnectivityDownEvent NOTIFICATION-TYPE
   OBJECTS { vmwEventSeverity, vmwAffectedObject, vmwOperatorDesc, vmwVrniUrl, vmwTimestamp, vmwEventName }
   STATUS current
   DESCRIPTION
      "NSX-T Edge Node is not able to communicate with any of the controllers.
      For more details, please log into vRNI, navigate to Settings -> Events"
   ::= { vmwVRNIEvents 80209}

vmwNSXTMtuMismatchEvent NOTIFICATION-TYPE
   OBJECTS { vmwEventSeverity, vmwAffectedObject, vmwOperatorDesc, vmwVrniUrl, vmwTimestamp, vmwEventName }
   STATUS current
   DESCRIPTION
      "The MTU configured on interface(s) of Tier-0 logical router do not match with the interface(s) of uplink switch/router from same L2 network. This may impact network performance.
      For more details, please log into vRNI, navigate to Settings -> Events"
   ::= { vmwVRNIEvents 80210}

vmwNSXEdgeBGPNeighbourDownEvent NOTIFICATION-TYPE
   OBJECTS { vmwEventSeverity, vmwAffectedObject, vmwOperatorDesc, vmwVrniUrl, vmwTimestamp, vmwEventName }
   STATUS current
   DESCRIPTION
      "One or more BGP neighbours are not in established state.
      For more details, please log into vRNI, navigate to Settings -> Events"
   ::= { vmwVRNIEvents 36067}

vmwAnalyticsEvent NOTIFICATION-TYPE
   OBJECTS { vmwEventSeverity, vmwAffectedObject, vmwOperatorDesc, vmwVrniUrl, vmwTimestamp, vmwEventName }
   STATUS current
   DESCRIPTION
      "Meta event for Analytics Event
      For more details, please log into vRNI, navigate to Settings -> Events"
   ::= { vmwVRNIEvents 37001}

vmwAnalyticsOutlierEvent NOTIFICATION-TYPE
   OBJECTS { vmwEventSeverity, vmwAffectedObject, vmwOperatorDesc, vmwVrniUrl, vmwTimestamp, vmwEventName }
   STATUS current
   DESCRIPTION
      "Meta event for Outlier Events
      For more details, please log into vRNI, navigate to Settings -> Events.
      "
   ::= { vmwVRNIEvents 37002}

vmwAnalyticsThresholdEvent NOTIFICATION-TYPE
   OBJECTS { vmwEventSeverity, vmwAffectedObject, vmwOperatorDesc, vmwVrniUrl, vmwTimestamp, vmwEventName }
   STATUS current
   DESCRIPTION
      "Meta event for Threshold Events
      For more details, please log into vRNI, navigate to Settings -> Events"
   ::= { vmwVRNIEvents 37003}

vmwVMCEvent NOTIFICATION-TYPE
   OBJECTS { vmwEventSeverity, vmwAffectedObject, vmwOperatorDesc, vmwVrniUrl, vmwTimestamp, vmwEventName }
   STATUS current
   DESCRIPTION
      "Meta event for VMC Events.
      For more details, please log into vRNI, navigate to Settings -> Events"
   ::= { vmwVRNIEvents 38001}

vmwPolicyManagerVrniDfwIPFixCollectorAbsent NOTIFICATION-TYPE
   OBJECTS { vmwEventSeverity, vmwAffectedObject, vmwOperatorDesc, vmwVrniUrl, vmwTimestamp, vmwEventName }
   STATUS current
   DESCRIPTION
      "Network Insight IPFIX Collector is absent on VMC Policy Manager.
      For more details, please log into vRNI, navigate to Settings -> Events"
   ::= { vmwVRNIEvents 80652}

vmwPolicyManagerNoDfwIPFixProfile NOTIFICATION-TYPE
   OBJECTS { vmwEventSeverity, vmwAffectedObject, vmwOperatorDesc, vmwVrniUrl, vmwTimestamp, vmwEventName }
   STATUS current
   DESCRIPTION
      "DFW IPFIX Profile is absent on VMC Policy Manager.
      For more details, please log into vRNI, navigate to Settings -> Events."
   ::= { vmwVRNIEvents 80651}

-- **********************************************************
-- Notification parameters
-- **********************************************************

vmwAffectedObject OBJECT-TYPE
    SYNTAX          SnmpAdminString
    MAX-ACCESS      accessible-for-notify
    STATUS          current
    DESCRIPTION
        "Object affected by this event"
    ::= { vmwVRNIData 102}


vmwEventSeverity OBJECT-TYPE
    SYNTAX          VmwVrniSeverity
    MAX-ACCESS      accessible-for-notify
    STATUS          current
    DESCRIPTION
        "vRNI Event Severity"
    ::= { vmwVRNIData 103}

vmwVrniUrl OBJECT-TYPE
    SYNTAX          SnmpAdminString
    MAX-ACCESS      accessible-for-notify
    STATUS          current
    DESCRIPTION
        "URL to vRNI for this exact event"
    ::= { vmwVRNIData 104}


vmwTimestamp OBJECT-TYPE
    SYNTAX          DateAndTime
    MAX-ACCESS      accessible-for-notify
    STATUS          current
    DESCRIPTION
        "Time of first detection of event"
    ::= { vmwVRNIData 105}

vmwOperatorDesc OBJECT-TYPE
    SYNTAX          VmwLongSnmpAdminString
    MAX-ACCESS      accessible-for-notify
    STATUS          current
    DESCRIPTION
        "Human readable message of the event"
    ::= { vmwVRNIData 106}

vmwEventName OBJECT-TYPE
    SYNTAX          VmwLongSnmpAdminString
    MAX-ACCESS      accessible-for-notify
    STATUS          current
    DESCRIPTION
        "Event name"
    ::= { vmwVRNIData 107}


-- conformance information
vmwNetworkInsightMIBConformance OBJECT IDENTIFIER ::= { vmwNetworkInsightMIB 99 }
vmwNetworkInsightMIBCompliances OBJECT IDENTIFIER ::=
                                        { vmwNetworkInsightMIBConformance 1 }
vmwNetworkInsightMIBGroups OBJECT IDENTIFIER ::= { vmwNetworkInsightMIBConformance 2 }

-- compliance statements
vmwNetworkInsightMIBBasicCompliance MODULE-COMPLIANCE
    STATUS     deprecated
    DESCRIPTION
        "The compliance statement for entities which implement
        VMWARE-NSX-MANAGER-MIB."
    MODULE -- this module
    MANDATORY-GROUPS { vmwNetworkInsightNotificationInfoGroup1,
                             vmwNetworkInsightNotificationGroup1 }
    ::= { vmwNetworkInsightMIBCompliances 3 }

vmwNetworkInsightNotificationInfoGroup1 OBJECT-GROUP
    OBJECTS {
    vmwAffectedObject,
    vmwEventSeverity,
    vmwVrniUrl,
    vmwTimestamp,
    vmwOperatorDesc,
    vmwEventName
    }
    STATUS current
    DESCRIPTION
    "These objects provide details in NSX Manager notifications."
    ::= { vmwNetworkInsightMIBGroups 2 }

vmwNetworkInsightNotificationGroup1 NOTIFICATION-GROUP
  NOTIFICATIONS {
    vmwSnmpTrapsAreConfigured,
        vmwSnmpTrapsAreDisabled,
        vmwTestTrap,
        vmwEntityDiscoveryChangeEvent,
        vmwEntityPropertiesChangeEvent,
        vmwFirewallNotInstalledOnHostEvent,
        vmwHostWithStaleFirewallRulesEvent,
        vmwIpAddressChangeEvent,
        vmwL2GatewayAnomalyEvent,
        vmwL2NetworkAddressAnomalyEvent,
        vmwL2NetworkDiameterExceededEvent,
        vmwL2NetworkUplinkMissingEvent,
        vmwL2NetworkWithNoVMsEvent,
        vmwLayer2NetworkDiameterChangedEvent,
        vmwMTUMismatchEvent,
        vmwNetworkIsolationEvent,
        vmwNoPathEvent,
        vmwSpoofguardDisabledEvent,
        vmwVMotionEvent,
        vmwVMWithDisconnectedVnicsEvent,
        vmwVMWithMulipleVnicsOnDifferentVxlansEvent,
        vmwVMWithMulipleVnicsOnSameL2Event,
        vmwVMWithNoIpAddressEvent,
        vmwVTEPMissingEvent,
        vmwL2Event,
        vmwMembershipChangeEvent,
        vmwSecurityGroupMembershipChangeEvent,
        vmwFirewallRuleMembershipChangeEvent,
        vmwVlanMembershipChangeEvent,
        vmwVxlanMembershipChangeEvent,
        vmwDeleteChangeEvent,
        vmwVtepFailedPingEvent,
        vmwEmptySearchStreamChangeEvent,
        vmwSearchStreamMembershipChangeEvent,
        vmwEmptySearchStreamProblemEvent,
        vmwSearchStreamMembershipProblemEvent,
        vmwOspfConfigurationMismatchEvent,
        vmwServiceVMNotHealthyEvent,
        vmwServiceVMNotPoweredOnEvent,
        vmwServiceVMHighCPUUsageEvent,
        vmwServiceVMHighMemoryUsageEvent,
        vmwServiceVMHighDiskUsageEvent,
        vmwIPSetPropertiesChangeEvent,
        vmwFirewallRulePropertiesChangeEvent,
        vmwSecurityGroupPropertiesChangeEvent,
        vmwIPSetMembershipChangeEvent,
        vmwFirewallRuleMaskEvent,
        vmwSecurityMembershipChangeEvent,
        vmwSecurityTagPropertiesChangeEvent,
        vmwSecurityTagMembershipChangeEvent,
        vmwHostDatastoreChangeEvent,
        vmwVMDatastoreChangeEvent,
        vmwVMSnapshotChangeEvent,
        vmwVMVirtualDiskChangeEvent,
        vmwIPSetDefinitionMismatchEvent,
        vmwSegmentMismatchEvent,
        vmwVtepEvent,
        vmwVtepConfigurationFaultEvent,
        vmwVtepSubnetMismatchEvent,
        vmwVtepCountMismatchEvent,
        vmwDLRNetworksNotReachableEvent,
        vmwEdgeNetworksNotReachableEvent,
        vmwThresholdExceededEventCpuReady,
        vmwThresholdExceededEventCpuCoStop,
        vmwThresholdExceededEventDiskCommandAbortRule,
        vmwThresholdExceededEventIODeviceLatencyRule,
        vmwThresholdExceededEventIOKernelLatencyRule,
        vmwThresholdExceededEventMemorySwapInRule,
        vmwThresholdExceededEventMemorySwapOutRule,
        vmwThresholdExceededEventNetworkRxDropRule,
        vmwThresholdExceededEventNetworkTxDropRule,
        vmwPacketDropEvent,
        vmwSwitchPortPacketDropEvent,
        vmwRouterInterfacePacketDropEvent,
        vmwVnicPacketDropEvent,
        vmwVTEPUnderlayPacketDropEvent,
        vmwPnicUnderlyingSwitchPortPacketDropEvent,
        vmwDevicePacketDropEvent,
        vmwThresholdExceededEventDatastoreFreeSpaceWarning,
        vmwThresholdExceededEventDatastoreFreeSpaceCritical,
        vmwThresholdExceededEventDatastoreReadLatency,
        vmwThresholdExceededEventDatastoreWriteLatency,
        vmwDistributedFirewallApplyHostEvent,
        vmwDistributedFirewallApplyVMEvent,
        vmwNsxEvent,
        vmwFeatureImpactedEvent,
        vmwClusterFeatureVersionMismatchEvent,
        vmwHostFeatureVersionMismatchEvent,
        vmwFeatureVersionMismatchEvent,
        vmwHostFeatureEnabledMismatchEvent,
        vmwHostFeatureInstalledMismatchEvent,
        vmwHostVtepNotFoundEvent,
        vmwHostVtepDisconnectedEvent,
        vmwHostVtepEvent,
        vmwClusterHostsVtepMTUMismatchEvent,
        vmwFeatureUnhealthyEvent,
        vmwEdgeHANotConfiguredEvent,
        vmwEdgeInterfacesDownEvent,
        vmwModuleUnhealthyEvent,
        vmwModuleNotLoadedEvent,
        vmwModuleNetworkConnectionFailureEvent,
        vmwHostNetworkControlPlaneMismatchEvent,
        vmwHostNetworkControlPlaneConnectionFailureEvent,
        vmwHostNetworkControlPlaneNotSyncedEvent,
        vmwNSXControllerClusterMajorityEvent,
        vmwNSXControllersVMOnSameHostEvent,
        vmwVxLanRangeExhaustEvent,
        vmwNSXFirewallDefaultAllowAllRulesEvent,
        vmwEdgeNotHAEvent,
        vmwEdgeNotDeployedEvent,
        vmwEcmpIsEnabledAndStatefulServicesAreUpEvent,
        vmwLogicalRouterDeployedOnEcmpEdgeHostEvent,
        vmwEdgeMissingInterfaceOSPFAreaMappingEvent,
        vmwOspfInsecureAuthRouterEvent,
        vmwNSXControllersDeployedCountEvent,
        vmwNSXControllerNotActiveCountEvent,
        vmwNSXControllerEvent,
        vmwNSXBackupEvent,
        vmwNSXUnsecureBackupEvent,
        vmwNSXBackupSystemEventsExcludedEvent,
        vmwNSXBackupNotScheduledEvent,
        vmwNSXBackupNotRecordedEvent,
        vmwNSXNtpServerEvent,
        vmwNSXSysLogServerEvent,
        vmwControllerSysLogServerEvent,
        vmwGenericNSXSystemEvent,
        vmwOtherCriticalNSXEvent,
        vmwFilterConfigApplyOnHostFailedEvent,
        vmwRulesetLoadOnHostFailedEvent,
        vmwConfigUpdateOnHostFailedEvent,
        vmwSpoofguardConfigUpdateOnHostFailedEvent,
        vmwApplyRuleToVnicFailedEvent,
        vmwContainerConfigUpdateOnVnicFailedEvent,
        vmwSpoofguardApplyToVnicFailedEvent,
        vmwHostMessagingConfigurationFailedEvent,
        vmwHostMessagingConnectionReconfigurationFailedEvent,
        vmwHostMessagingConfigurationFailedNotificationSkippedEvent,
        vmwHostMessagingInfrastructureDownEvent,
        vmwEdgeVMNotRespondingEvent,
        vmwEdgeUnhealthyEvent,
        vmwEdgeVMCommunicationFailureEvent,
        vmwNSXEdgeEvent,
        vmwPanEvent,
        vmwPanNsxNotInRegisteredStateEvent,
        vmwPanNsxDynamicUpdateDelayedEvent,
        vmwPanDeviceInDisconnectedStateEvent,
        vmwPanNsxServiceApplianceViewMismatchEvent,
        vmwPanNsxFabricAgentNotFoundOnHostEvent,
        vmwPanNsxServiceVMNotFoundOnHostEvent
}
    STATUS current
    DESCRIPTION
    "Set of notifications (traps, informs) supported in this version."
    ::= { vmwNetworkInsightMIBGroups 3 }

vmwNetworkInsightMIBBasicCompliance2 MODULE-COMPLIANCE
    STATUS     deprecated
    DESCRIPTION
        "The compliance statement for entities which implement
         VMWARE-VRNI-MIB second version."
    MODULE -- this module
    MANDATORY-GROUPS { vmwNetworkInsightNotificationInfoGroup2,
                       vmwNetworkInsightNotificationGroup1,
                       vmwNetworkInsightNotificationGroup2
                      }
    ::= { vmwNetworkInsightMIBCompliances 30 }

vmwNetworkInsightNotificationInfoGroup2 OBJECT-GROUP
    OBJECTS {
    vmwAffectedObject,
    vmwEventSeverity,
    vmwVrniUrl,
    vmwTimestamp,
    vmwOperatorDesc,
    vmwEventName
    }
    STATUS deprecated
    DESCRIPTION
    "These events provide details in NSX Manager notifications."
    ::= { vmwNetworkInsightMIBGroups 20 }

vmwNetworkInsightNotificationGroup2 NOTIFICATION-GROUP
       NOTIFICATIONS {
       vmwLogicalRouterNoUplinkEvent,
       vmwNSXComponentEvent,
       vmwNSXBackupEvent,
       vmwNSXBackupAuditLogExcludedEvent,
       vmwNSXUnsecureBackupEvent,
       vmwNSXBackupSystemEventsExcludedEvent,
       vmwNSXBackupNotScheduledEvent,
       vmwNSXBackupNotRecordedEvent,
       vmwNSXNtpServerEvent,
       vmwNSXSysLogServerEvent,
       vmwControllerSysLogServerEvent
       }
       STATUS current
       DESCRIPTION
            "Set of added notifications (traps, informs) since last revision."
        ::= { vmwNetworkInsightMIBGroups 30 }

vmwNetworkInsightMIBBasicCompliance3 MODULE-COMPLIANCE
    STATUS     deprecated
    DESCRIPTION
        "The compliance statement for entities which implement
         VMWARE-VRNI-MIB second version."
    MODULE -- this module
    MANDATORY-GROUPS { vmwNetworkInsightNotificationInfoGroup2,
                       vmwNetworkInsightNotificationGroup1,
                       vmwNetworkInsightNotificationGroup2,
                       vmwNetworkInsightNotificationGroup3
                      }
    ::= { vmwNetworkInsightMIBCompliances 35 }

vmwNetworkInsightNotificationGroup3 NOTIFICATION-GROUP
       NOTIFICATIONS {
        vmwMTUMismatchEvent,
        vmwVMWithMulipleVnicsOnSameL2Event,
        vmwMembershipChangeEvent,
        vmwSecurityGroupMembershipChangeEvent,
        vmwFirewallRuleMembershipChangeEvent,
        vmwVlanMembershipChangeEvent,
        vmwVxlanMembershipChangeEvent,
        vmwSearchStreamMembershipChangeEvent,
        vmwIPSetMembershipChangeEvent,
        vmwSecurityMembershipChangeEvent,
        vmwVtepEvent,
        vmwPacketDropEvent,
        vmwSwitchPortPacketDropEvent,
        vmwRouterInterfacePacketDropEvent,
        vmwVnicPacketDropEvent,
        vmwVTEPUnderlayPacketDropEvent,
        vmwPnicUnderlyingSwitchPortPacketDropEvent,
        vmwHostFeatureVersionMismatchEvent,
        vmwSpoofguardConfigUpdateOnHostFailedEvent,
        vmwNSXEcmpEdgeDownEvent,
        vmwNSXMajorityEcmpEdgesDownEvent,
        vmwNSXAllEcmpEdgesDownEvent
       }
       STATUS current
       DESCRIPTION
            "Set of added notifications (traps, informs) since last revision."
        ::= { vmwNetworkInsightMIBGroups 40 }

vmwNetworkInsightMIBBasicCompliance4 MODULE-COMPLIANCE
    STATUS     deprecated
    DESCRIPTION
        "The compliance statement for entities which implement
         VMWARE-VRNI-MIB second version."
    MODULE -- this module
    MANDATORY-GROUPS { vmwNetworkInsightNotificationInfoGroup2,
                       vmwNetworkInsightNotificationGroup1,
                       vmwNetworkInsightNotificationGroup2,
                       vmwNetworkInsightNotificationGroup3,
                       vmwNetworkInsightNotificationGroup4
                      }
    ::= { vmwNetworkInsightMIBCompliances 45 }

vmwNetworkInsightNotificationGroup4 NOTIFICATION-GROUP
       NOTIFICATIONS {
       vmwNSXEdgeSplitBrainEvent,
       vmwNSXIpV6EnabledEvent,
       vmwNSXOspfNeighborDownEvent,
       vmwCheckpointEvent,
       vmwNSXEdgeMtuMismatchEvent,
       vmwCheckpointNsxFabricAgentNotFoundOnHostEvent,
       vmwCheckpointNsxServiceVMNotFoundOnHostEvent,
       vmwCheckpointGatewaySicStatusNotCommunicatingEvent,
       vmwCheckpointNsxServiceApplianceViewMismatchEvent,
       vmwCriticalHostNotAccessibleEvent,
       vmwVlanMembershipChangeEvent,
       vmwClusterFeatureVersionMismatchEvent,
       vmwHostFeatureVersionMismatchEvent,
       vmwConfigUpdateOnHostFailedEvent
       }
       STATUS current
       DESCRIPTION
            "Set of added notifications (traps, informs) since last revision."
        ::= { vmwNetworkInsightMIBGroups 50 }

vmwNetworkInsightNotificationInfoGroup3 OBJECT-GROUP
    OBJECTS {
    vmwEventSeverity,
    vmwAffectedObject,
    vmwOperatorDesc,
    vmwVrniUrl,
    vmwTimestamp,
    vmwEventName
    }
    STATUS current
    DESCRIPTION
    "These objects provide details in VRNI notifications."
    ::= { vmwNetworkInsightMIBGroups 55 }

vmwNetworkInsightMIBBasicCompliance5 MODULE-COMPLIANCE
    STATUS     deprecated
    DESCRIPTION
        "The compliance statement for entities which implement
         VMWARE-VRNI-MIB latest version."
    MODULE -- this module
    MANDATORY-GROUPS { vmwNetworkInsightNotificationInfoGroup3,
                       vmwNetworkInsightNotificationGroup1,
                       vmwNetworkInsightNotificationGroup2,
                       vmwNetworkInsightNotificationGroup3,
                       vmwNetworkInsightNotificationGroup4,
                       vmwNetworkInsightNotificationGroup5
                      }
    ::= { vmwNetworkInsightMIBCompliances 60 }

vmwNetworkInsightMIBBasicCompliance6 MODULE-COMPLIANCE
    STATUS     current
    DESCRIPTION
        "The compliance statement for entities which implement
         VMWARE-VRNI-MIB latest version."
    MODULE -- this module
    MANDATORY-GROUPS { vmwNetworkInsightNotificationInfoGroup3,
                       vmwNetworkInsightNotificationGroup1,
                       vmwNetworkInsightNotificationGroup2,
                       vmwNetworkInsightNotificationGroup3,
                       vmwNetworkInsightNotificationGroup4,
                       vmwNetworkInsightNotificationGroup5,
                       vmwNetworkInsightNotificationGroup6
                      }
    ::= { vmwNetworkInsightMIBCompliances 70 }

vmwNetworkInsightNotificationGroup5 NOTIFICATION-GROUP
       NOTIFICATIONS {
          vmwNiInfraChangeEvent,
          vmwDataSourceEnabledChangeEvent,
          vmwDataSourceDisabledChangeEvent,
          vmwDataSourceCreatedEvent,
          vmwPlatformCpuCoreChangeEvent,
          vmwPlatformDiskChangeEvent,
          vmwPlatformMemoryChangeEvent,
          vmwPlatformRebootedEvent,
          vmwProxyCpuCoreChangeEvent,
          vmwProxyDiskChangeEvent,
          vmwProxyMemoryChangeEvent,
          vmwProxyRebootedEvent,
          vmwNIClusterChangeEvent,
          vmwNISystemProxyChangeEvent,
          vmwNIClusterCreateEvent,
          vmwAWSRegionSGLimitEvent,
          vmwAWSVPCSGLimitEvent,
          vmwAWSSGInboundRuleLimitEvent,
          vmwAWSSGOutboundRuleLimitEvent,
          vmwAWSInterfaceSGLimitEvent,
          vmwVirtualDistributedRoutingEvent,
          vmwIndexerLagEvent,
          vmwIPFIXFlowDPPausedEvent,
          vmwGridProcessingStoppedEvent,
          vmwUnableToSendEmailsEvent,
          vmwSMTPNotConfiguredEvent,
          vmwSNMPNotConfiguredEvent,
          vmwReindexingInProgressEvent,
          vmwNodesVersionMismatchEvent,
          vmwNotAllServicesRunningEvent,
          vmwNotAllServicesHealthyEvent,
          vmwExpandPartitionFailedEvent,
          vmwDiskCleanupFailedEvent,
          vmwVaccumFailedEvent,
          vmwConfigStoreCleanupFailedEvent,
          vmwHBaseRetentionToolFailedEvent,
          vmwMetricStoreUpdaterFailedEvent,
          vmwCollectorLagEvent,
          vmwCollectionLagEvent,
          vmwGridProcessingLagEvent,
          vmwConnectionErrorEvent,
          vmwNodeNotActiveEvent,
          vmwHighDiskUtilizationEvent,
          vmwIndexingAbortedEvent,
          vmwUpgradeFailedEvent,
          vmwFlowProcessingSuspendedEvent,
          vmwVCNotOnSameProxyEvent,
          vmwNoDVSAvailableEvent,
          vmwUnknownInfobloxVersionEvent,
          vmwUnsupportedInfobloxVersionEvent,
          vmwIncorrectInfobloxCredentialEvent,
          vmwInfobloxRecordLimitExceededEvent,
          vmwWebhookNotRunningEvent,
          vmwIncorrectWebhookConfiguredOnAlertEvent,
          vmwWebhookNotEnabledOnAlertEvent,
          vmwVRNIContentPackNotInstalledEvent,
          vmwUnsupportedVRNIContentPackVersionEvent,
          vmwUnsupportedLogInsightVersionEvent,
          vmwComputeManagersNotAddedEvent,
          vmwComputeManagersNotFoundEvent,
          vmwUnsupportedNSXTVersionEvent,
          vmwNotEmptyNodeEvent,
          vmwFlowPhysicalNodeEvent,
          vmwFlowCollectionErrorEvent,
          vmwAWSThrottlingExceptionEvent,
          vmwAWSFlowLogAccessDeniedExceptionEvent,
          vmwNSXIPFIXStatusMismatchEvent,
          vmwNumVMsOrHostsNotFoundEvent,
          vmwUnsupportedNSXVersionEvent,
          vmwPwdAuthModeDisabledAristaEvent,
          vmwHostnameResolutionErrorEvent,
          vmwPrimaryNSXNotAddedEvent,
          vmwDataProviderNotRunningEvent,
          vmwInvalidResponseFromDatasourceEvent,
          vmwHostNotReachableEvent,
          vmwNSXControllerNotFoundEvent,
          vmwUnexpectedDSTypeOrVersionEvent,
          vmwWarnConfigEvent,
          vmwInvalidConfigEvent,
          vmwNotFoundEvent,
          vmwInsufficientPrivilegesEvent,
          vmwPwdAuthModeDisabledEvent,
          vmwFailedCredsEncryptEvent,
          vmwSNMPConnectionInvalidEvent,
          vmwUnknownHostEvent,
          vmwInvalidCredentialsEvent,
          vmwIncorrectConnectionStringEvent,
          vmwConnectionRefusedEvent,
          vmwTimeoutEvent,
          vmwFailedEvent,
          vmwNSXTEvent,
          vmwNSXTVcNotAddedEvent,
          vmwNSXTStandaloneHostsEvent,
          vmwLargeSdmsDroppedEvent,
          vmwNSXTIPFixDFWStatusNotEnabledEvent,
          vmwNSXTIPFixPortIncorrectEvent,
          vmwNSXTIPFixCollectorAndIPFixProfileMismatchEvent,
          vmwNSXTIPFixIPFixProfilePriorityNotZeroEvent,
          vmwNSXTIPFixNoIPFixProfileEvent,
          vmwNSXTIPFixNoNewCollectorProfileCanBeAddedEvent,
          vmwNSXTIPFixNoCollectorProfileEvent
          }
       STATUS current
       DESCRIPTION
            "Set of added notifications (traps, informs) since last revision."
        ::= { vmwNetworkInsightMIBGroups 65 }

  vmwNetworkInsightNotificationGroup6 NOTIFICATION-GROUP
       NOTIFICATIONS {
          vmwNSXTSystemEvent,
          vmwNSXTNoUplinkConnectivityEvent,
          vmwNSXTRoutingAdvertisementEvent,
          vmwNSXTManagerConnectivityDownEvent,
          vmwNSXTControllerConnectivityDegradedEvent,
          vmwNSXTControllerConnectivityDownEvent,
          vmwNSXTMtuMismatchEvent,
          vmwNSXEdgeBGPNeighbourDownEvent,
          vmwAnalyticsEvent,
          vmwAnalyticsOutlierEvent,
          vmwAnalyticsThresholdEvent,
          vmwVMCEvent,
          vmwPolicyManagerVrniDfwIPFixCollectorAbsent,
          vmwPolicyManagerNoDfwIPFixProfile
       }
       STATUS current
       DESCRIPTION
            "Set of added notifications (traps, informs) for 4.0.0 release."
        ::= { vmwNetworkInsightMIBGroups 75 }

END
