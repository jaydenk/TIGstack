-- **********************************************************
-- Copyright 2018 VMware, Inc.  All rights reserved.
-- **********************************************************

VMW-TUNNEL-SERVER-AGENTCAP-MIB DEFINITIONS ::= BEGIN

IMPORTS
    MODULE-IDENTITY
        FROM SNMPv2-SMI
    vmwareAgentCapabilities
        FROM VMWARE-ROOT-MIB
    AGENT-CAPABILITIES
        FROM  SNMPv2-CONF;


vmwTunnelServerAgentCapMIB MODULE-IDENTITY
    LAST-UPDATED "201809040000Z"
    ORGANIZATION "VMware, Inc."
    CONTACT-INFO
        "VMware, Inc.
        3401 Hillview Ave
        Palo Alto, CA 94304
        Tel: 1-877-486-9273 or 650-427-5000
        Fax: 650-427-5001
        Web: https://kb.vmware.com/s/article/1013445
        "
    DESCRIPTION
        "This module defines agent capabilities for deployed VMware Tunnel Server by release."

    REVISION     "201809040000Z"
    DESCRIPTION
        "Capabilities for VMware Tunnel Server 4.0.0 release."
        ::= { vmwareAgentCapabilities 28 }

vmwTunnelServerCapability OBJECT IDENTIFIER ::= { vmwTunnelServerAgentCapMIB 1 }


--
-- Applies to 4.0.0 Release
--


vmwTunnelServer2018-400 AGENT-CAPABILITIES
    PRODUCT-RELEASE
        "4.0.0"
    STATUS  current
    DESCRIPTION
        "Release 4.0.0 for VMware Tunnel Server supporting tunnel
         statistic and information queries.
        "
    REFERENCE
        "https://www.vmware.com/products/workspace-one.html"
    SUPPORTS VMWARE-TUNNEL-SERVER-MIB    -- REVISION 201808300000Z

    INCLUDES {
        vmwTunnelServerStatGroup,
        vmwTunnelServerInfoGroup
    }
    ::= { vmwTunnelServerCapability 1 }


END
